TIMETRA-BGP-MIB DEFINITIONS ::= BEGIN

IMPORTS
    bgp4PathAttrIpAddrPrefix,
    bgp4PathAttrIpAddrPrefixLen,
    bgp4PathAttrPeer
                                                         FROM BGP4-MIB
    InterfaceIndex
                                                         FROM IF-MIB
    InetAddress, InetAddressPrefixLength,
    InetAddressType,
    InetAutonomousSystemNumber
                                                         FROM INET-ADDRESS-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DisplayString, RowStatus,
    TEXTUAL-CONVENTION, TestAndIncr,
    TimeStamp, TruthValue
                                                         FROM SNMPv2-TC
    TFilterLogId
                                                         FROM TIMETRA-FILTER-MIB
    timetraSRMIBModules, tmnxSRConfs,
    tmnxSRNotifyPrefix, tmnxSRObjs
                                                         FROM TIMETRA-GLOBAL-MIB
    BgpConnectRetryTime, BgpHoldTime,
    TBgpSrv6UpaTriggerNextHop,
    TBgpUntaggedRouteType,
    TLNamedItemOrEmpty,
    TLPolicyNameOrExpOrEmpty,
    TLPolicyStatementNameOrEmpty,
    TNamedItem, TNamedItemOrEmpty,
    TPolicyStatementNameOrEmpty,
    TResolveStatus, TSrv6RouteResolution,
    TXLPolicyNameOrExpOrEmpty,
    TmnxAdminState,
    TmnxAdminStateTruthValue,
    TmnxBGPFamilyType,
    TmnxBgpAutonomousSystem,
    TmnxBgpLocalPreference,
    TmnxBgpPreference, TmnxCreateOrigin,
    TmnxDPathDomainId, TmnxEnabledDisabled,
    TmnxHigh32, TmnxLow32, TmnxOperState,
    TmnxPrefixSidFullRange,
    TmnxVPNRouteDistinguisher, TmnxVRtrID
                                                         FROM TIMETRA-TC-MIB
    vRtrID
                                                         FROM TIMETRA-VRTR-MIB
    ;

timetraBgpMIBModule              MODULE-IDENTITY
    LAST-UPDATED "202302150000Z"
    ORGANIZATION "Nokia"
    CONTACT-INFO
        "Nokia SROS Support
         Web: http://www.nokia.com"
    DESCRIPTION
        "This document is the SNMP MIB module for Nokia's implementation of
         BGP.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification.

         There is one BGP instance per virtual router.  Each BGP instance
         can have a number of peer groups.

         The MIB objects here are organized in to four groups:
         - global objects (nothing there for now)
         - per-instance objects
         - per-peer group objects
         - per-peer objects

         The value of most BGP configuration objects can be defaulted at three
         levels: at the per-peer level, at the peer group level, and at the
         BGP instance level.  The per-peer object values are set:
         - first by the peer object value, if set;
         - second, if not set then by the peer group object value, if that is
           set;
         - third, if not set, by the instance object value."

    REVISION    "202302150000Z"
    DESCRIPTION
        "Rev 23               15 Feb 2023 00:00
         release 23 of the TIMETRA-BGP-MIB."

    REVISION    "201701010000Z"
    DESCRIPTION
        "Rev 15.0               1 Jan 2017 00:00
         15.0 release of the TIMETRA-BGP-MIB."

    REVISION    "201601010000Z"
    DESCRIPTION
        "Rev 14.0               1 Jan 2016 00:00
         14.0 release of the TIMETRA-BGP-MIB."

    REVISION    "201501010000Z"
    DESCRIPTION
        "Rev 13.0               1 Jan 2015 00:00
         13.0 release of the TIMETRA-BGP-MIB."

    REVISION    "201401010000Z"
    DESCRIPTION
        "Rev 12.0               1 Jan 2014 00:00
         12.0 release of the TIMETRA-BGP-MIB."

    REVISION    "201102010000Z"
    DESCRIPTION
        "Rev 9.0                1 Feb 2011 00:00
         0.0 release of the TIMETRA-BGP-MIB."

    REVISION    "200902280000Z"
    DESCRIPTION
        "Rev 7.0                28 Feb 2009 00:00
         7.0 release of the TIMETRA-BGP-MIB."

    REVISION    "200807010000Z"
    DESCRIPTION
        "Rev 6.1                01 Jul 2008 00:00
         6.1 release of the TIMETRA-BGP-MIB."

    REVISION    "200801010000Z"
    DESCRIPTION
        "Rev 6.0                01 Jan 2008 00:00
         6.0 release of the TIMETRA-BGP-MIB."

    REVISION    "200701010000Z"
    DESCRIPTION
        "Rev 5.0                01 Jan 2007 00:00
         5.0 release of the TIMETRA-BGP-MIB."

    REVISION    "200603150000Z"
    DESCRIPTION
        "Rev 4.0                15 Mar 2006 00:00
         4.0 release of the TIMETRA-BGP-MIB."

    REVISION    "200508310000Z"
    DESCRIPTION
        "Rev 3.0                31 Aug 2005 00:00
         3.0 release of the TIMETRA-BGP-MIB."

    REVISION    "200501240000Z"
    DESCRIPTION
        "Rev 2.1                24 Jan 2005 00:00
         2.1 release of the TIMETRA-BGP-MIB."

    REVISION    "200401150000Z"
    DESCRIPTION
        "Rev 2.0                15 Jan 2004 00:00
         2.0 release of the TIMETRA-BGP-MIB."

    REVISION    "200308150000Z"
    DESCRIPTION
        "Rev 1.2                15 Aug 2003 00:00
         1.2 release of the TIMETRA-BGP-MIB."

    REVISION    "200301200000Z"
    DESCRIPTION
        "Rev 1.0                    20 Jan 2003 00:00
         1.0 Release of the TIMETRA-BGP-MIB"

    REVISION    "200106130000Z"
    DESCRIPTION
        "Rev 0.1                    13 Jun 2001 00:00
         Initial version of the TIMETRA-BGP-MIB"

    ::= { timetraSRMIBModules 14 }

BgpKeepAliveTime                 ::= TEXTUAL-CONVENTION
    STATUS      current
    DESCRIPTION
        "a time interval in seconds for the Keep Alive timer."
    REFERENCE
        "BGP4-MIB.bgpPeerKeepAlive"
    SYNTAX      Integer32 (0 | 1..21845)

BgpMinASOriginationTime          ::= TEXTUAL-CONVENTION
    STATUS      current
    DESCRIPTION
        "a time interval in seconds for the minimum AS
         Origination Time.  Suggested default is 15 seconds."
    REFERENCE
        "BGP4-MIB.bgpPeerMinASOriginationInterval"
    SYNTAX      Integer32 (2..255)

BgpLoopDetect                    ::= TEXTUAL-CONVENTION
    STATUS      current
    DESCRIPTION
        "Determines how the peer session should deal with loop detection in the
         AS path.

         drop : Send a Notification to remote peer and drop session
         ignore : Ignore routes with loops in the the AS Path but maintain
                  peering
         off : Turn off loop detection"
    SYNTAX      INTEGER {
        drop         (1),
        ignore       (2),
        off          (3),
        discardRoute (4)
    }

BgpMinRouteAdvertisement         ::= TEXTUAL-CONVENTION
    STATUS      current
    DESCRIPTION
        "Determines the minimal interval (in seconds) at with a given path
         attribute can be advertised to a peer."
    SYNTAX      Integer32 (1..255)

BgpMEDSource                     ::= TEXTUAL-CONVENTION
    STATUS      current
    DESCRIPTION
        "The source of the Multi Exit Discriminator in the advertisement"
    SYNTAX      INTEGER {
        igpCost   (1),
        metricVal (2),
        noMedOut  (3)
    }

BgpMEDValue                      ::= TEXTUAL-CONVENTION
    STATUS      current
    DESCRIPTION
        "a Multi Exit Discriminator value."
    REFERENCE
        "RFC 1771"
    SYNTAX      Unsigned32

BgpTimeToLive                    ::= TEXTUAL-CONVENTION
    STATUS      current
    DESCRIPTION
        "Time To Live (TTL) value for IP packet header."
    SYNTAX      Integer32 (0..255)

BgpMultiPath                     ::= TEXTUAL-CONVENTION
    STATUS      current
    DESCRIPTION
        "BGP Multipath max-path value.  one means disabled, no multipath."
    SYNTAX      Integer32 (1..64)

BgpPeerGroupName                 ::= TEXTUAL-CONVENTION
    STATUS      current
    DESCRIPTION
        "the name of a Peer Group."
    SYNTAX      DisplayString (SIZE (1..64))

BgpPeerGroupNameOrEmpty          ::= TEXTUAL-CONVENTION
    STATUS      current
    DESCRIPTION
        "the name of a Peer Group."
    SYNTAX      DisplayString (SIZE (0..64))

BgpPrefixLimit                   ::= TEXTUAL-CONVENTION
    STATUS      current
    DESCRIPTION
        "BGP prefix learning count limit.  zero means no prefix learning limit."
    SYNTAX      Unsigned32

BgpPeerType                      ::= TEXTUAL-CONVENTION
    STATUS      current
    DESCRIPTION
        "the type of BGP peer, internal or external."
    SYNTAX      INTEGER {
        noType   (1),
        internal (2),
        external (3)
    }

BgpPeerState                     ::= TEXTUAL-CONVENTION
    STATUS      current
    DESCRIPTION
        "The BGP peer connection state."
    REFERENCE
        "BGP4-MIB, OBJECT-TYPE bgpPeerState"
    SYNTAX      INTEGER {
        idle        (1),
        connect     (2),
        active      (3),
        opensent    (4),
        openconfirm (5),
        established (6)
    }

BgpPeerEvent                     ::= TEXTUAL-CONVENTION
    STATUS      current
    DESCRIPTION
        "BGP peer events.

         The event 'none' implies that the peer is in initialization phase.

         The event 'start' implies that BGP operation has started on this peer.

         The event 'stop' implies that BGP operation has stopped on this peer.

         The event 'open' implies that BGP transport has initialized a
         connection open action to the peer.

         The event 'close' implies that BGP transport has closed the connection
         to the peer.

         The event 'openFail' implies that open connection attempt of BGP
         transport has failed.

         The event 'error' implies that BGP transport experienced a fatal
         error.

         The event 'connectionRetry' implies that the connection retry timer
         expired.

         The event 'holdTime' implies that the hold timer expired.

         The event 'keepAlive' implies that the keep alive timer expired.

         The event 'receiveOpen' implies that a BGP OPEN message was received.

         The event 'receiveKeepAlive' implies that a BGP KEEPALIVE was
         received.

         The event 'receiveUpdate ' implies that a BGP UPDATE was received.

         The event 'receiveNotify' implies that a BGP NOTIFY was received.

         The event 'startPassive' implies that BGP is waiting passive to hear
         from the other end.

         The event 'parseError' implies that there was a bad message received
         from the peer.

         The event 'outOfMemory' implies that there is not enough memory in the
         system for this peer entity.

         The event 'rtmLimitExceeded' implies that the route table max limit
         has exceeded.

         The event 'maxPrefixLimitExceeded' implies that the max prefixes
         allowed has been exceeded.

         The event 'maxPrefixLimitExceededLogged' implies that the max prefixes
         allowed has been exceeded but the peering is not dropped.

         The event 'outOfProtectedNHIndex' implies that protected next hop
         indexes has been exceeded.

         The event 'outOfNHIndex' implies that next hop indexes has been
         exceeded.

         The event 'labelAllocFailed' implies that label allocation failed.

         The event 'lspIdAllocFailed' implies that LSP Id allocation failed.

         The event 'collisionResolution' implies that bgp peering is down due
         to collision resolution process.

         The event 'adminShutdown' implies that BGP peering is brought down due
         to a shutdown of BGP peer, group or protocol.

         The event 'adminReset' implies that bgp peering is brought down due to
         a clear of BGP peer, group or protocol.

         The event 'configChange' implies that bgp peering is brought down due
         to a configuration change which requires reestablishment."
    SYNTAX      INTEGER {
        none                         (0),
        start                        (1),
        stop                         (2),
        open                         (3),
        close                        (4),
        openFail                     (5),
        error                        (6),
        connectionRetry              (7),
        holdTime                     (8),
        keepAlive                    (9),
        receiveOpen                  (10),
        receiveKeepAlive             (11),
        receiveUpdate                (12),
        receiveNotify                (13),
        startPassive                 (14),
        parseError                   (15),
        outOfMemory                  (16),
        rtmLimitExceeded             (17),
        maxPrefixLimitExceeded       (18),
        maxPrefixLimitExceededLogged (19),
        outOfProtectedNHIndex        (20),
        outOfNHIndex                 (21),
        labelAllocFailed             (22),
        lspIdAllocFailed             (23),
        collisionResolution          (24),
        adminShutdown                (25),
        adminReset                   (26),
        configChange                 (27),
        peerTrackingPolicyMismatch   (28),
        receivedMalformedAttr        (29),
        adminResetHard               (30),
        peerDamping                  (31)
    }

BgpOperState                     ::= TEXTUAL-CONVENTION
    STATUS      current
    DESCRIPTION
        "The BgpOperState data type is an enumerated integer that describes the
         values used to identify the current operational state of functional
         modules. In addition to the four states that are also a part of
         TmnxOperState, we have a fifth state 'disabled' which indicates that
         the operational state is down and requires user intervention."
    SYNTAX      INTEGER {
        unknown      (1),
        inService    (2),
        outOfService (3),
        transition   (4),
        disabled     (5)
    }

TmnxIpFamily                     ::= TEXTUAL-CONVENTION
    STATUS      current
    DESCRIPTION
        "The value of TmnxIpFamily specifies the types of Network Layer Routing
         Information (NLRI) to be distributed by BGP. BGP was initially
         designed for the distribution of IPv4 routing information.
         Multi-protocol extensions such as IPv6, VPN-IPv4 and VPN-IPv6,
         MVPN-IPv4 and MVPN-IPv6, L2-VPN addresses, and many more have been
         added to extend its ability to carry overlapping routing information.
         At the current time, NLRI for 21 address families can be carried in
         MP-BGP.

         The first address family is plain 'IPv4 (1)'. The NLRI for this
         address family was described in RFC1771, which was the original BGPv4
         RFC. (RFC1771 was later obsoleted by RFC4271). Therefor the NLRI does
         not need to be encapsulated in Multi-Protocol BGP. IPv4 is the only
         address family that does not need to be encapsulated in MP-BGP.

         All following address families are transported using Multi-Protocol
         BGP. MP-BGP was first described in RFC2283, which is obsoleted by
         RFC4760.

         A 'vpnIpv4 (2)' NLRI is a an IPv4 prefix advertised in the context of
         a Virtual Private Network (VPN). The format of a vpnIpv4 NLRI is a
         12-byte value consisting of an 8-byte Route Distinguisher (RD), and
         the 4-byte ipv4 IP prefix. The RD must be unique within the scope of
         the VPRN. This allows the IP address prefixes within different VRFs to
         overlap. IPv4 VPNs were first described in RFC2547, which was
         obsoleted by RFC4364.

         An 'ipv6 (3)' NLRI is an IPv6 prefix, used for natively routing IPv6.
         See RFC2545.

         An 'mcastIpv4 (4)' NLRI is an ipv4 prefix that can be used for the
         Reverse Path Forwarding check (RPF) in multicast-routing. This allows
         a network to have a incongruent topology for unicast routing and
         multicast-routing.

         A 'vpnIpv6 (5)' NLRI is an address from family 'ipv6 (3)' carried
         inside a VPN. The format is a 24-byte value consisting of the 8-byte
         RD, and 16 bytes for the IPv6 prefix. When both IPv4 and IPv6 VPRN
         services are enabled, the PE router uses the same RD for both address
         families. See RFC4659.

         A 'l2vpn (6)' address is a 12-byte Virtual Switch Instance identifier
         (VSI-ID) value consisting of the 8-byte route distinguisher(RD)
         followed by a 4-byte value.

         A 'mvpnIpv4  (7)' address is variable size value consisting of the
         1-byte route type, 1-byte length and variable size route type specific.
         The content of these NLRI are PIM messages. See RFC6513.

         A 'mdtSafi (8)' address is a 16-byte value consisting of 12-byte route
         distinguisher(RD) followed by a 4-byte group address.

         A 'mspw (9)' address is a dynamic multi-segment pseudowire address.

         A 'flowIpv4 (10)' address is a variable size value consisting of 1 or
         2-byte NLRI (Network Layer Reachability Information) length followed
         by a variable length NLRI value.

         A 'routeTarget (11)' address is a variable size value consisting of
         zero length or 12 byte (ipv4) or 24 byte (ipv6) NLRI (Network Layer
         Reachability Information) length followed by a variable length NLRI
         value.

         A 'mcastVpnIpv4(12)' NLRI is an address from family 'mcastIpv4 (4)'
         carried inside a VPN. The format is a 12-byte value consisting of the
         8-byte RD and 4 bytes for the IPv4 prefix. This allows customers to
         have incongruent unicast and multicast topologies over a VPN.

         A 'mvpnIpv6 (13)' address is variable size value consisting of the
         1-byte route type, 1-byte length and variable size route type
         specific. The content of these NLRI are PIM messages. See RFC6513.

         A 'flowIpv6 (14)' address is a variable size value consisting of 1 or
         2-byte NLRI(Network Layer Reachability Information) length followed by
         a variable length NLRI value.

         A 'evpn (15)' address is variable size value consisting of the 1-byte
         route type, 1-byte length and variable size route type specific. Route
         type defines encoding for the route type specific field. Length
         indicates the length in octets of the route type specific field.

         A 'mcastIpv6 (16)' NLRI is similar to 'mcastIpv4 (4)', but for IPv6.
         The mcastIpv6 NLRI is an ipv6 prefix that can be used for the Reverse
         Path Forwarding check (RPF) in multicast-routing. This allows a
         network to have a incongruent topology for unicast IPv6 routing and
         multicast-IPv6-routing.

         A 'bgpLs (19)' NLRI is a piece of information that has been taken from
         the Link-State Database of IS-IS or OSPF, and is transported via BGP
         to a controller. This can e.g. be a SDN-controller, or a network
         management station.

         A 'mcastVpnIpv6 (20)' NLRI is a prefix from family 'mcastIpv6 (16)'
         carried inside a VPN. The format is a 24-byte value consisting of the
         8-byte RD and 16 bytes for the IPv6 prefix. This allows customers to
         have incongruent unicast and multicast IPv6-topologies over a VPN.

         If any address type is added to TmnxIpFamily, the same address type
         should also be added in TmnxIpFamilyIdentifier."
    SYNTAX      BITS {
        unused       (0),
        ipv4         (1),
        vpnIpv4      (2),
        ipv6         (3),
        mcastIpv4    (4),
        vpnIpv6      (5),
        l2vpn        (6),
        mvpnIpv4     (7),
        mdtSafi      (8),
        mspw         (9),
        flowIpv4     (10),
        routeTarget  (11),
        mcastVpnIpv4 (12),
        mvpnIpv6     (13),
        flowIpv6     (14),
        evpn         (15),
        mcastIpv6    (16),
        labelIpv4    (17),
        labelIpv6    (18),
        bgpLs        (19),
        mcastVpnIpv6 (20),
        srplcyIpv4   (21),
        srplcyIpv6   (22),
        flowVpnIpv4  (23),
        flowVpnIpv6  (24)
    }

TmnxVpnCapability                ::= TEXTUAL-CONVENTION
    STATUS      current
    DESCRIPTION
        "The value of TmnxVpnCapability specifies the route negotiation types a
         BGP peer is capable of using."
    SYNTAX      BITS {
        routeRefresh      (0),
        mpBGP             (1),
        orfExtendCommSend (2),
        orfExtendCommRecv (3),
        asn4Byte          (4),
        extNHEncoding     (5),
        bfdStrictMode     (6)
    }

TmnxAdvLabelAddressFamily        ::= TEXTUAL-CONVENTION
    STATUS      current
    DESCRIPTION
        "The value of TmnxAdvLabelAddressFamily specifies the address family
         for the advertisement label."
    SYNTAX      BITS {
        none (0),
        ipv6 (1),
        ipv4 (2)
    }

TmnxAddPathAddressFamily         ::= TEXTUAL-CONVENTION
    STATUS      current
    DESCRIPTION
        "The value of TmnxAddPathAddressFamily specifies the address family for
         BGP ADD-PATH."
    SYNTAX      BITS {
        none       (0),
        ipv4       (1),
        vpnIpv4    (2),
        ipv6       (3),
        vpnIpv6    (4),
        labelIpv4  (5),
        labelIpv6  (6),
        mvpnIpv4   (7),
        mvpnIpv6   (8),
        mcastVpnV4 (9),
        mcastVpnV6 (10),
        evpn       (11)
    }

TmnxAddPathSendLimit             ::= TEXTUAL-CONVENTION
    STATUS      current
    DESCRIPTION
        "The value of TmnxAddPathSendLimit specifies the maximum number of
         paths that can be advertised to ADD-PATH peers per prefix.

         The value -1 indicates that BGP must send exactly the number of best
         multipaths it has for each NLRI."
    SYNTAX      Integer32 (-1 | 0..16)

TmnxBgpFlowRouteExtCommAction    ::= TEXTUAL-CONVENTION
    STATUS      current
    DESCRIPTION
        "The value of TmnxBgpFlowRouteExtCommAction specifies the extended
         community action."
    SYNTAX      INTEGER {
        unknown       (0),
        rateLimit     (1),
        sampleLog     (2),
        redirectToVrf (3),
        nextEntry     (4),
        markDscp      (5),
        redirectToIp  (6),
        redirectToIf  (7),
        redirectToLsp (8),
        flowspecSet   (9)
    }

TmnxIpNhChgFamily                ::= TEXTUAL-CONVENTION
    STATUS      current
    DESCRIPTION
        "The value of TmnxIpNhChgFamily specifies the address family for which
         the ebgp next-hop should remain unchanged."
    SYNTAX      BITS {
        labelIpv4 (0),
        labelIpv6 (1),
        vpnIpv4   (2),
        vpnIpv6   (3),
        evpn      (4)
    }

TmnxIpFamilyIdentifier           ::= TEXTUAL-CONVENTION
    STATUS      current
    DESCRIPTION
        "The value of TmnxIpFamilyIdentifier is an enumerated integer that
         describes the information about the address family. The values in
         TmnxIpFamilyIdentifier correspond to those in TmnxIpFamily.

         If any address type is added to TmnxIpFamilyIdentifier, the same
         address type should also be added in TmnxIpFamily."
    SYNTAX      INTEGER {
        unused       (0),
        ipv4         (1),
        vpnIpv4      (2),
        ipv6         (3),
        mcastIpv4    (4),
        vpnIpv6      (5),
        l2vpn        (6),
        mvpnIpv4     (7),
        mdtSafi      (8),
        mspw         (9),
        flowIpv4     (10),
        routeTarget  (11),
        mcastVpnIpv4 (12),
        mvpnIpv6     (13),
        flowIpv6     (14),
        evpn         (15),
        mcastIpv6    (16),
        labelIpv4    (17),
        labelIpv6    (18),
        bgpLs        (19),
        mcastVpnIpv6 (20),
        srplcyIpv4   (21),
        srplcyIpv6   (22),
        flowVpnIpv4  (23),
        flowVpnIpv6  (24)
    }

TBgpNHResolutionTunnelType       ::= TEXTUAL-CONVENTION
    STATUS      current
    DESCRIPTION
        "TBgpNHResolutionTunnelType specifies next-hop resolution tunnel types."
    SYNTAX      BITS {
        ldp               (0),
        srIsis            (1),
        srOspfV2          (2),
        srOspfV3          (3),
        srPolicyColored   (4),
        srPolicyUncolored (5),
        vxlan             (6),
        bgp               (7)
    }

TBgpSendCommType                 ::= TEXTUAL-CONVENTION
    STATUS      current
    DESCRIPTION
        "The value of TBgpSendCommType specifies the send community type."
    SYNTAX      BITS {
        none     (0),
        standard (1),
        extended (2),
        large    (3)
    }

tBgpObjects                      OBJECT IDENTIFIER ::= { tmnxSRObjs 14 }

tBgpGlobalObjects                OBJECT IDENTIFIER ::= { tBgpObjects 1 }

tBgpInstanceObjects              OBJECT IDENTIFIER ::= { tBgpObjects 2 }

tBgpInstanceTableLastChanged     OBJECT-TYPE
    SYNTAX      TimeStamp
    MAX-ACCESS  read-only
    STATUS      current
    DESCRIPTION
        "The value of tBgpInstanceTableLastChanged indicates the last timestamp
         when an entry in the tBgpPeerGroupTable was last changed."
    ::= { tBgpInstanceObjects 1 }

tBgpInstanceTable                OBJECT-TYPE
    SYNTAX      SEQUENCE OF TBgpInstanceEntry
    MAX-ACCESS  not-accessible
    STATUS      current
    DESCRIPTION
        "tBgpInstanceTable consists of information about each running instance
         of BGP."
    ::= { tBgpInstanceObjects 2 }

tBgpInstanceEntry                OBJECT-TYPE
    SYNTAX      TBgpInstanceEntry
    MAX-ACCESS  not-accessible
    STATUS      current
    DESCRIPTION
        "An entry (conceptual row) in the tBgpInstanceTable. each entry
         represents an instance of BGP running on the virtual router."
    INDEX       { tBgpInstanceIndex }
    ::= { tBgpInstanceTable 1 }

TBgpInstanceEntry                ::= SEQUENCE
{
    tBgpInstanceIndex                TmnxVRtrID,
    tBgpInstanceRowStatus            RowStatus,
    tBgpInstanceShutdown             TmnxAdminStateTruthValue,
    tBgpInstanceDescription          DisplayString,
    tBgpInstanceAlwaysCompareMED     INTEGER,
    tBgpInstanceAsPathIgnore         TruthValue,
    tBgpInstanceBgpId                IpAddress,
    tBgpInstanceConnectRetry         BgpConnectRetryTime,
    tBgpInstanceHoldTime             BgpHoldTime,
    tBgpInstanceKeepAlive            BgpKeepAliveTime,
    tBgpInstanceMinASOrigination     BgpMinASOriginationTime,
    tBgpInstanceDampening            TruthValue,
    tBgpInstanceLocalAS              TmnxBgpAutonomousSystem,
    tBgpInstanceLocalPreference      TmnxBgpLocalPreference,
    tBgpInstanceLoopDetect           BgpLoopDetect,
    tBgpInstanceMinRouteAdvertisement BgpMinRouteAdvertisement,
    tBgpInstanceMultipath            BgpMultiPath,
    tBgpInstanceNoAggregatorID       TruthValue,
    tBgpInstancePreference           TmnxBgpPreference,
    tBgpInstanceRemovePrivateAS      TruthValue,
    tBgpInstanceLastChanged          TimeStamp,
    tBgpInstanceMultihop             BgpTimeToLive,
    tBgpInstanceMEDSource            BgpMEDSource,
    tBgpInstanceMEDValue             BgpMEDValue,
    tBgpInstanceConfederationAS      TmnxBgpAutonomousSystem,
    tBgpInstanceImportPolicy1        TPolicyStatementNameOrEmpty,
    tBgpInstanceImportPolicy2        TPolicyStatementNameOrEmpty,
    tBgpInstanceImportPolicy3        TPolicyStatementNameOrEmpty,
    tBgpInstanceImportPolicy4        TPolicyStatementNameOrEmpty,
    tBgpInstanceImportPolicy5        TPolicyStatementNameOrEmpty,
    tBgpInstanceExportPolicy1        TPolicyStatementNameOrEmpty,
    tBgpInstanceExportPolicy2        TPolicyStatementNameOrEmpty,
    tBgpInstanceExportPolicy3        TPolicyStatementNameOrEmpty,
    tBgpInstanceExportPolicy4        TPolicyStatementNameOrEmpty,
    tBgpInstanceExportPolicy5        TPolicyStatementNameOrEmpty,
    tBgpInstanceOperStatus           BgpOperState,
    tBgpInstanceLocalASPrivate       TruthValue,
    tBgpInstanceMd5Auth              TruthValue,
    tBgpInstanceMd5AuthKey           DisplayString,
    tBgpInstanceClusterId            IpAddress,
    tBgpInstanceDisableClientReflect TruthValue,
    tBgpInstanceIBgpMultipath        TruthValue,
    tBgpInstanceFamily               TmnxIpFamily,
    tBgpInstanceGracefulRestart      TruthValue,
    tBgpInstanceGRPathSelectDefer    Unsigned32,
    tBgpInstanceGRRestartTime        Unsigned32,
    tBgpInstanceGRStaleRoute         Unsigned32,
    tBgpInstanceGRAdminState         TmnxAdminState,
    tBgpInstanceGROperState          TmnxOperState,
    tBgpInstanceVpnApplyImport       TruthValue,
    tBgpInstanceVpnApplyExport       TruthValue,
    tBgpInstanceIgpShortcut          BITS,
    tBgpInstanceDisallowIgp          TruthValue,
    tBgpInstanceOrf                  TruthValue,
    tBgpInstanceExtCommsOrf          TruthValue,
    tBgpInstanceExtCommsSendOrf      TruthValue,
    tBgpInstanceExtCommsRecvOrf      TruthValue,
    tBgpInstanceAllowInterAsVpn      TruthValue,
    tBgpInstancePurgeTimer           Unsigned32,
    tBgpInstanceLocalAS4Byte         InetAutonomousSystemNumber,
    tBgpInstanceConfederationAS4Byte InetAutonomousSystemNumber,
    tBgpInstanceDisable4ByteASN      TruthValue,
    tBgpInstanceMultipathEiBgpState  TmnxEnabledDisabled,
    tBgpInstanceHoldTimeIsStrict     TruthValue,
    tBgpInstanceAsPathIgnoreFamily   TmnxIpFamily,
    tBgpInstanceRemovePrivateASLmtd  TruthValue,
    tBgpInstancePMTUDiscovery        TruthValue,
    tBgpInstanceDisableRtTblInstall  TruthValue,
    tBgpInstanceNHResUseBgpRoutes    TruthValue,
    tBgpInstanceEnableRRVpnFwding    TruthValue
}

tBgpInstanceIndex                OBJECT-TYPE
    SYNTAX      TmnxVRtrID
    MAX-ACCESS  not-accessible
    STATUS      current
    DESCRIPTION
        "The value of tBgpInstanceIndex specifies the index for the
         tBgpInstanceTable."
    ::= { tBgpInstanceEntry 1 }

tBgpInstanceRowStatus            OBJECT-TYPE
    SYNTAX      RowStatus
    MAX-ACCESS  read-create
    STATUS      current
    DESCRIPTION
        "The value of tBgpInstanceRowStatus specifies the row status for this
         BGP instance for the virtual router. It is used to create and delete
         row entries in this table.

         In order for an attempt to 'destroy' this row entry to succeed, the
         value of tBgpInstanceShutdown must be 'true' and the value of
         vRtrBgpStatus must be 'delete'.

         In order for an attempt to 'create' this row entry, the value of
         vRtrBgpStatus must be 'create'."
    ::= { tBgpInstanceEntry 2 }

tBgpInstanceShutdown             OBJECT-TYPE
    SYNTAX      TmnxAdminStateTruthValue
    MAX-ACCESS  read-create
    STATUS      current
    DESCRIPTION
        "The value of tBgpInstanceShutdown specifies whether or not this BGP
         instance is disabled or shutdown. When the value of this object is
         'false', the BGP instance is enabled."
    DEFVAL      { false }
    ::= { tBgpInstanceEntry 3 }

tBgpInstanceDescription          OBJECT-TYPE
    SYNTAX      DisplayString (SIZE (0..80))
    MAX-ACCESS  read-create
    STATUS      current
    DESCRIPTION
        "The value of tBgpInstanceDescription specifies the textual description
         of this BGP instance."
    DEFVAL      { ''H }
    ::= { tBgpInstanceEntry 4 }

tBgpInstanceAlwaysCompareMED     OBJECT-TYPE
    SYNTAX      INTEGER {
        off      (1),
        zero     (2),
        infinity (3),
        on       (4)
    }
    MAX-ACCESS  read-create
    STATUS      current
    DESCRIPTION
        "The state of tBgpInstanceAlwaysCompareMED specifies whether Multi-Exit
         Discriminator (MED) path attribute will be compared when coming from
         different AS and used in the BGP route selection process.

         A state of 'off' specifies that only the MEDs of routes that have the
         same peer ASs are compared.

         A state of 'on' specifies that the Multi-Exit Discriminator (MED)
         value will be compared when coming from different ASs and if one of
         the route has no MED it should be assigned the lowest possible value
         of 'zero'.

         A value of 'zero' or 'infinity' specifies that the MED attribute is
         always used in the route selection process regardless of the peer AS
         that advertised the route. If the route does not have MED it is
         assigned the value of 'zero' or 'infinity' respectively."
    DEFVAL      { off }
    ::= { tBgpInstanceEntry 5 }

tBgpInstanceAsPathIgnore         OBJECT-TYPE
    SYNTAX      TruthValue
    MAX-ACCESS  read-create
    STATUS      obsolete
    DESCRIPTION
        "This object was obsoleted in release 8.0. It is replaced with the
         object tBgpInstanceAsPathIgnoreFamily."
    DEFVAL      { false }
    ::= { tBgpInstanceEntry 6 }

tBgpInstanceBgpId                OBJECT-TYPE
    SYNTAX      IpAddress
    MAX-ACCESS  read-create
    STATUS      current
    DESCRIPTION
        "The value of tBgpInstanceBgpId specifies the BGP instance id. This
         object is required to be set before the instance can be activated."
    DEFVAL      { '00000000'H }
    ::= { tBgpInstanceEntry 7 }

tBgpInstanceConnectRetry         OBJECT-TYPE
    SYNTAX      BgpConnectRetryTime
    UNITS       "seconds"
    MAX-ACCESS  read-create
    STATUS      current
    DESCRIPTION
        "The value of tBgpInstanceConnectRetry specifies the value (in seconds)
         for the BGP Connect Retry timer."
    REFERENCE
        "BGP4-MIB.bgpPeerConnectRetryInterval"
    DEFVAL      { 120 }
    ::= { tBgpInstanceEntry 8 }

tBgpInstanceHoldTime             OBJECT-TYPE
    SYNTAX      BgpHoldTime
    UNITS       "seconds"
    MAX-ACCESS  read-create
    STATUS      current
    DESCRIPTION
        "The value of tBgpInstanceHoldTime specifies the value (in seconds) for
         BGP Hold Time."
    REFERENCE
        "BGP4-MIB.bgpPeerHoldTime"
    DEFVAL      { 90 }
    ::= { tBgpInstanceEntry 9 }

tBgpInstanceKeepAlive            OBJECT-TYPE
    SYNTAX      BgpKeepAliveTime
    UNITS       "seconds"
    MAX-ACCESS  read-create
    STATUS      current
    DESCRIPTION
        "The value of tBgpInstanceKeepAlive specifies the value (in seconds)
         for BGP Keepalive timer. A keepalive message is sent every time this
         timer expires."
    REFERENCE
        "BGP4-MIB.bgpPeerKeepAlive"
    DEFVAL      { 30 }
    ::= { tBgpInstanceEntry 10 }

tBgpInstanceMinASOrigination     OBJECT-TYPE
    SYNTAX      BgpMinASOriginationTime
    UNITS       "seconds"
    MAX-ACCESS  read-create
    STATUS      obsolete
    DESCRIPTION
        "The value of tBgpInstanceMinASOrigination specifies the minimal
         interval (in seconds) at which a given path attribute can be
         advertised to a peer.

         This object was obsoleted in release 12.0."
    REFERENCE
        "BGP4-MIB.bgpPeerMinASOriginationInterval"
    DEFVAL      { 15 }
    ::= { tBgpInstanceEntry 11 }

tBgpInstanceDampening            OBJECT-TYPE
    SYNTAX      TruthValue
    MAX-ACCESS  read-create
    STATUS      current
    DESCRIPTION
        "The value of tBgpInstanceDampening specifies if route dampening is
         applied to learned routes."
    DEFVAL      { false }
    ::= { tBgpInstanceEntry 12 }

tBgpInstanceLocalAS              OBJECT-TYPE
    SYNTAX      TmnxBgpAutonomousSystem
    MAX-ACCESS  read-create
    STATUS      obsolete
    DESCRIPTION
        "The value of tBgpInstanceLocalAS specifies the autonomous system
         number to be advertised for peers under this instance.

         This object was obsoleted in release 7.0.  It is replaced with the
         4-byte AS number defined by tBgpInstanceLocalAS4Byte."
    DEFVAL      { 0 }
    ::= { tBgpInstanceEntry 13 }

tBgpInstanceLocalPreference      OBJECT-TYPE
    SYNTAX      TmnxBgpLocalPreference
    MAX-ACCESS  read-create
    STATUS      current
    DESCRIPTION
        "The value of tBgpInstanceLocalPreference specifies the default value
         for the Local Preference attribute. This value is used if the BGP
         route arrives from a BGP peer without the Local Preference attribute
         set.

         It is overridden by any value set via a route policy."
    DEFVAL      { 100 }
    ::= { tBgpInstanceEntry 14 }

tBgpInstanceLoopDetect           OBJECT-TYPE
    SYNTAX      BgpLoopDetect
    MAX-ACCESS  read-create
    STATUS      current
    DESCRIPTION
        "The value of tBgpInstanceLoopDetect determines how the peer session
         should deal with loop detection in the AS Path."
    DEFVAL      { ignore }
    ::= { tBgpInstanceEntry 15 }

tBgpInstanceMinRouteAdvertisement OBJECT-TYPE
    SYNTAX      BgpMinRouteAdvertisement
    UNITS       "seconds"
    MAX-ACCESS  read-create
    STATUS      current
    DESCRIPTION
        "The value of tBgpInstanceMinRouteAdvertisement specifies the minimum
         interval at which a given path attribute is advertised to a peer."
    DEFVAL      { 30 }
    ::= { tBgpInstanceEntry 16 }

tBgpInstanceMultipath            OBJECT-TYPE
    SYNTAX      BgpMultiPath
    UNITS       "number-of-hops"
    MAX-ACCESS  read-create
    STATUS      obsolete
    DESCRIPTION
        "The value of tBgpInstanceMultipath specifies if BGP multipath is
         enabled or disabled for this instance.

         A value of '1' would disable BGP multipath.

         Any other value would specify the number of hops for BGP Multipath."
    DEFVAL      { 1 }
    ::= { tBgpInstanceEntry 17 }

tBgpInstanceNoAggregatorID       OBJECT-TYPE
    SYNTAX      TruthValue
    MAX-ACCESS  read-create
    STATUS      current
    DESCRIPTION
        "The value of tBgpInstanceNoAggregatorID specifies if different routers
         in the same AS create aggregate routes containing different AS paths.

         A value of 'true' would enable setting the router ID to 0 in the
         aggregator path attribute when BGP is aggregating routes.

         A value of 'false' would disable setting the router ID to 0 in the
         aggregator path attribute when BGP is aggregating routes."
    DEFVAL      { false }
    ::= { tBgpInstanceEntry 18 }

tBgpInstancePreference           OBJECT-TYPE
    SYNTAX      TmnxBgpPreference (1..255)
    MAX-ACCESS  read-create
    STATUS      current
    DESCRIPTION
        "The value of tBgpInstancePreference specifies the route preference for
         routes learned via the peer."
    DEFVAL      { 170 }
    ::= { tBgpInstanceEntry 19 }

tBgpInstanceRemovePrivateAS      OBJECT-TYPE
    SYNTAX      TruthValue
    MAX-ACCESS  read-create
    STATUS      current
    DESCRIPTION
        "The value of tBgpInstanceRemovePrivateAS specifies if private AS
         numbers should be stripped from the AS Path before advertising them to
         BGP peers."
    DEFVAL      { false }
    ::= { tBgpInstanceEntry 20 }

tBgpInstanceLastChanged          OBJECT-TYPE
    SYNTAX      TimeStamp
    MAX-ACCESS  read-only
    STATUS      current
    DESCRIPTION
        "The value tBgpInstanceLastChanged indicates when an entry in
         tBgpInstanceTable was last changed."
    ::= { tBgpInstanceEntry 21 }

tBgpInstanceMultihop             OBJECT-TYPE
    SYNTAX      BgpTimeToLive
    UNITS       "TTL hops"
    MAX-ACCESS  read-create
    STATUS      current
    DESCRIPTION
        "The value of tBgpInstanceMultihop specifies the TTL used in IP packet
         header for BGP advertisements.

         Default TTL values for EBGP peer is 1, and MAX_TTL for IBGP peers.
         Default value if not set is  no_type - the peer has to infer its value
         based on local-as, and peer-as in that case."
    DEFVAL      { 0 }
    ::= { tBgpInstanceEntry 22 }

tBgpInstanceMEDSource            OBJECT-TYPE
    SYNTAX      BgpMEDSource
    MAX-ACCESS  read-create
    STATUS      current
    DESCRIPTION
        "The value of tBgpInstanceMEDSource specifies the source of the Multi
         Exit Discriminator (MED) value for this peer."
    DEFVAL      { noMedOut }
    ::= { tBgpInstanceEntry 23 }

tBgpInstanceMEDValue             OBJECT-TYPE
    SYNTAX      BgpMEDValue
    MAX-ACCESS  read-create
    STATUS      current
    DESCRIPTION
        "The value of tBgpInstanceMEDValue specifies the value of MED when
         tBgpInstanceMEDSource is 'metricVal'. If the value of
         tBgpInstanceMEDSource is not 'metricVal', this object is ignored."
    DEFVAL      { 0 }
    ::= { tBgpInstanceEntry 24 }

tBgpInstanceConfederationAS      OBJECT-TYPE
    SYNTAX      TmnxBgpAutonomousSystem
    MAX-ACCESS  read-only
    STATUS      obsolete
    DESCRIPTION
        "The value of tBgpInstanceConfederationAS specifies the confederation
         AS for this BGP instance.

         A value of '0' means no confederation AS.

         This object was obsoleted in release 7.0.  It is replaced with
         the 4-byte AS number defined by tBgpInstanceConfederationAS4Byte."
    ::= { tBgpInstanceEntry 25 }

tBgpInstanceImportPolicy1        OBJECT-TYPE
    SYNTAX      TPolicyStatementNameOrEmpty
    MAX-ACCESS  read-create
    STATUS      obsolete
    DESCRIPTION
        "The value of tBgpInstanceImportPolicy1 specifies import policy number
         1 for peer level.

         This object was obsoleted in release 10.0. It is replaced by object
         tBgpInstancePlcyImportPolicy1."
    DEFVAL      { ''H }
    ::= { tBgpInstanceEntry 30 }

tBgpInstanceImportPolicy2        OBJECT-TYPE
    SYNTAX      TPolicyStatementNameOrEmpty
    MAX-ACCESS  read-create
    STATUS      obsolete
    DESCRIPTION
        "The value of tBgpInstanceImportPolicy2 specifies import policy number
         2 for peer level.

         This object was obsoleted in release 10.0. It is replaced by object
         tBgpInstancePlcyImportPolicy2."
    DEFVAL      { ''H }
    ::= { tBgpInstanceEntry 31 }

tBgpInstanceImportPolicy3        OBJECT-TYPE
    SYNTAX      TPolicyStatementNameOrEmpty
    MAX-ACCESS  read-create
    STATUS      obsolete
    DESCRIPTION
        "The value of tBgpInstanceImportPolicy3 specifies import policy number
         3 for peer level.

         This object was obsoleted in release 10.0. It is replaced by object
         tBgpInstancePlcyImportPolicy3."
    DEFVAL      { ''H }
    ::= { tBgpInstanceEntry 32 }

tBgpInstanceImportPolicy4        OBJECT-TYPE
    SYNTAX      TPolicyStatementNameOrEmpty
    MAX-ACCESS  read-create
    STATUS      obsolete
    DESCRIPTION
        "The value of tBgpInstanceImportPolicy4 specifies import policy number
         4 for peer level.

         This object was obsoleted in release 10.0. It is replaced by object
         tBgpInstancePlcyImportPolicy4."
    DEFVAL      { ''H }
    ::= { tBgpInstanceEntry 33 }

tBgpInstanceImportPolicy5        OBJECT-TYPE
    SYNTAX      TPolicyStatementNameOrEmpty
    MAX-ACCESS  read-create
    STATUS      obsolete
    DESCRIPTION
        "The value of tBgpInstanceImportPolicy5 specifies import policy number
         5 for peer level.

         This object was obsoleted in release 10.0. It is replaced by object
         tBgpInstancePlcyImportPolicy5."
    DEFVAL      { ''H }
    ::= { tBgpInstanceEntry 34 }

tBgpInstanceExportPolicy1        OBJECT-TYPE
    SYNTAX      TPolicyStatementNameOrEmpty
    MAX-ACCESS  read-create
    STATUS      obsolete
    DESCRIPTION
        "The value of tBgpInstanceExportPolicy1 specifies export policy number
         1 for peer level.

         This object was obsoleted in release 10.0. It is replaced by object
         tBgpInstancePlcyExportPolicy1."
    DEFVAL      { ''H }
    ::= { tBgpInstanceEntry 35 }

tBgpInstanceExportPolicy2        OBJECT-TYPE
    SYNTAX      TPolicyStatementNameOrEmpty
    MAX-ACCESS  read-create
    STATUS      obsolete
    DESCRIPTION
        "The value of tBgpInstanceExportPolicy2 specifies export policy number
         2 for peer level.

         This object was obsoleted in release 10.0. It is replaced by object
         tBgpInstancePlcyExportPolicy2."
    DEFVAL      { ''H }
    ::= { tBgpInstanceEntry 36 }

tBgpInstanceExportPolicy3        OBJECT-TYPE
    SYNTAX      TPolicyStatementNameOrEmpty
    MAX-ACCESS  read-create
    STATUS      obsolete
    DESCRIPTION
        "The value of tBgpInstanceExportPolicy3 specifies export policy number
         3 for peer level.

         This object was obsoleted in release 10.0. It is replaced by object
         tBgpInstancePlcyExportPolicy3."
    DEFVAL      { ''H }
    ::= { tBgpInstanceEntry 37 }

tBgpInstanceExportPolicy4        OBJECT-TYPE
    SYNTAX      TPolicyStatementNameOrEmpty
    MAX-ACCESS  read-create
    STATUS      obsolete
    DESCRIPTION
        "The value of tBgpInstanceExportPolicy4 specifies export policy number
         4 for peer level.

         This object was obsoleted in release 10.0. It is replaced by object
         tBgpInstancePlcyExportPolicy4."
    DEFVAL      { ''H }
    ::= { tBgpInstanceEntry 38 }

tBgpInstanceExportPolicy5        OBJECT-TYPE
    SYNTAX      TPolicyStatementNameOrEmpty
    MAX-ACCESS  read-create
    STATUS      obsolete
    DESCRIPTION
        "The value of tBgpInstanceExportPolicy5 specifies export policy number
         5 for peer level.

         This object was obsoleted in release 10.0. It is replaced by object
         tBgpInstancePlcyExportPolicy5."
    DEFVAL      { ''H }
    ::= { tBgpInstanceEntry 39 }

tBgpInstanceOperStatus           OBJECT-TYPE
    SYNTAX      BgpOperState
    MAX-ACCESS  read-only
    STATUS      current
    DESCRIPTION
        "The value of tBgpInstanceOperStatus indicates the operational status
         of the BGP instance for the virtual router.

         A value of 'inService(2)' means the bgp instance is fully functional.

         A value of 'outOfService(3)' means the bgp instance is down.

         A value of 'transition(4)' means the bgp instance is performing a
         transition from state inService(2) to outOfService(3) or vice versa.

         A value of 'disabled(5)' means the BGP instance needs to be restarted
         by the user."
    ::= { tBgpInstanceEntry 40 }

tBgpInstanceLocalASPrivate       OBJECT-TYPE
    SYNTAX      TruthValue
    MAX-ACCESS  read-create
    STATUS      current
    DESCRIPTION
        "The value of tBgpInstanceLocalASPrivate specifies if the local
         autonomous system number is hidden in paths learned from peering.

         When the value of tBgpInstanceLocalAS4Byte is changed, the value of
         tBgpInstanceLocalASPrivate is reset to its default value.

         An 'inconsistentValue' error is returned if an attempt is made to set
         this object to a non-default value when the value of object
         tBgpInstanceLocalAS4Byte is not set to non-default value."
    DEFVAL      { false }
    ::= { tBgpInstanceEntry 41 }

tBgpInstanceMd5Auth              OBJECT-TYPE
    SYNTAX      TruthValue
    MAX-ACCESS  read-create
    STATUS      current
    DESCRIPTION
        "The value of tBgpInstanceMd5Auth specifies if the authentication using
         MD5 message based digest protocol is enabled."
    DEFVAL      { false }
    ::= { tBgpInstanceEntry 42 }

tBgpInstanceMd5AuthKey           OBJECT-TYPE
    SYNTAX      DisplayString (SIZE (0..255))
    MAX-ACCESS  read-create
    STATUS      current
    DESCRIPTION
        "The value of tBgpInstanceMd5AuthKey specifies the authentication key
         to be used between BGP peers neighbors before establishing sessions.

         Authentication is done using the MD5 message based digest protocol.

         Authentication can be configured globally and applied to all BGP peers
         or per group or per peer. The most specific value is used.

         The authentication key can be any combination of letters or numbers.
         Note that the string CANNOT contain embedded nulls."
    DEFVAL      { ''H }
    ::= { tBgpInstanceEntry 43 }

tBgpInstanceClusterId            OBJECT-TYPE
    SYNTAX      IpAddress
    MAX-ACCESS  read-create
    STATUS      current
    DESCRIPTION
        "This value of tBgpInstanceClusterId specifies the cluster ID for a
         route reflector server.

         A value of 0.0.0.0 indicates that no cluster ID has been assigned to
         the BGP instance."
    DEFVAL      { '00000000'H }
    ::= { tBgpInstanceEntry 44 }

tBgpInstanceDisableClientReflect OBJECT-TYPE
    SYNTAX      TruthValue
    MAX-ACCESS  read-create
    STATUS      current
    DESCRIPTION
        "The value of tBgpInstanceDisableClientReflect specifies if reflection
         of routes by the route reflector to all client peers within its
         cluster is enabled or disabled.

         A value of 'false' means reflection of routes to all client peers is
         enabled."
    DEFVAL      { false }
    ::= { tBgpInstanceEntry 45 }

tBgpInstanceIBgpMultipath        OBJECT-TYPE
    SYNTAX      TruthValue
    MAX-ACCESS  read-create
    STATUS      current
    DESCRIPTION
        "The value of tBgpInstanceIBgpMultipath specifies if load sharing is
         enabled among multiple IBGP paths.

         A value of 'false' disables IBGP Multipath."
    DEFVAL      { false }
    ::= { tBgpInstanceEntry 46 }

tBgpInstanceFamily               OBJECT-TYPE
    SYNTAX      TmnxIpFamily
    MAX-ACCESS  read-create
    STATUS      current
    DESCRIPTION
        "The value of tBgpInstanceFamily specifies the types of routing
         information to be distributed by this instance of BGP.  BGP was
         initially designed for the distribution of IPv4 routing information.
         Multi-protocol extensions and the use of a VPN-IPv4, VPN-IPv6, MVPN-IPv4
         and L2-VPN addresses have been added to extend its ability to carry
         overlapping routing information.

         A 'vpnIpv4 (2)' address is a 12-byte value consisting of
         the 8-byte route distinguisher, RD, and the 4-byte ipv4 IP address
         prefix.  The RD must be unique within the scope of the VPRN.
         This allows the IP address prefixes within different VRFs to
         overlap.

         'ipv6 (3)', 'mcastIpv4 (4)', 'l2vpn (6)' and 'mcastVpnIpv4 (12)' are
         multi-protocol extensions to BGP.

         'mcastIpv6 (16)' is part of multi-protocol extension to BGP.

         A 'vpnIpv6 (5)' address is a 24-byte value consisting of the 8-byte
         RD, and 16 bytes for the IPv6 address. When both IPv4 and IPv6 VPRN
         services are enabled, the PE router uses the same RD for both address
         families.

         A 'l2vpn (6)' address is a 12-byte Virtual Switch Instance identifier
         (VSI-ID) value consisting of the 8-byte route distinguisher(RD)
         followed by a 4-byte value.

         A 'mvpnIpv4  (7)' address is variable size value consisting of the
         1-byte route type, 1-byte length and variable size route type specific.
         Route type defines encoding for the route type specific field. Length
         indicates the length in octets of the route type specific field.

         A 'mdtSafi (8)' address is a 16-byte value consisting of 12-byte route
         distinguisher(RD) followed by a 4-byte group address.

         A 'mspw (9)' address is a dynamic multi-segment pseudowire address.

         A 'flowIpv4 (10)' address is a variable size value consisting of 1 or
         2-byte NLRI(Network Layer Reachability Information) length followed by
         a variable length NLRI value.

         A 'routeTarget (11)' address is a variable size value consisting of
         zero length or 12 byte (ipv4) or 24 byte (ipv6) NLRI (Network Layer
         Reachability Information) length followed by a variable length NLRI
         value.

         A 'mvpnIpv6 (13)' address is variable size value consisting of the
         1-byte route type, 1-byte length and variable size route type
         specific. Route type defines encoding for the route type specific
         field. Length indicates the length in octets of the route type
         specific field.

         A 'flowIpv6 (14)' address is a variable size value consisting of 1 or
         2-byte NLRI(Network Layer Reachability Information) length followed by
         a variable length NLRI value.

         A 'evpn (15)' address is variable size value consisting of the 1-byte
         route type, 1-byte length and variable size route type specific. Route
         type defines encoding for the route type specific field. Length
         indicates the length in octets of the route type specific field."
    DEFVAL      { {ipv4} }
    ::= { tBgpInstanceEntry 47 }

tBgpInstanceGracefulRestart      OBJECT-TYPE
    SYNTAX      TruthValue
    MAX-ACCESS  read-create
    STATUS      current
    DESCRIPTION
        "The value of tBgpInstanceGracefulRestart specifies whether or not
         graceful restart capabilities are enabled on this instance of BGP.

         When the value is set to 'false' graceful restart is disabled and any
         previous configuration of other graceful restart parameters is
         removed."
    DEFVAL      { false }
    ::= { tBgpInstanceEntry 48 }

tBgpInstanceGRPathSelectDefer    OBJECT-TYPE
    SYNTAX      Unsigned32 (1..3600)
    UNITS       "seconds"
    MAX-ACCESS  read-create
    STATUS      current
    DESCRIPTION
        "The value of tBgpInstanceGRPathSelectDefer specifies the time limit in
         seconds for restarting BGP instance to defer path selection logic."
    DEFVAL      { 120 }
    ::= { tBgpInstanceEntry 49 }

tBgpInstanceGRRestartTime        OBJECT-TYPE
    SYNTAX      Unsigned32 (0..4095)
    UNITS       "seconds"
    MAX-ACCESS  read-create
    STATUS      current
    DESCRIPTION
        "The value of tBgpInstanceGRRestartTime specifies the maximum amount of
         time in seconds that a graceful restart should take."
    DEFVAL      { 120 }
    ::= { tBgpInstanceEntry 50 }

tBgpInstanceGRStaleRoute         OBJECT-TYPE
    SYNTAX      Unsigned32 (1..3600)
    UNITS       "seconds"
    MAX-ACCESS  read-create
    STATUS      current
    DESCRIPTION
        "The value of tBgpInstanceGRStaleRoute specifies the maximum amount of
         time in seconds that stale routes should be maintained after a
         graceful restart is initiated. This value should be at least as large
         as the value of tBgpInstanceGRRestartTime."
    DEFVAL      { 360 }
    ::= { tBgpInstanceEntry 51 }

tBgpInstanceGRAdminState         OBJECT-TYPE
    SYNTAX      TmnxAdminState
    MAX-ACCESS  read-create
    STATUS      current
    DESCRIPTION
        "The value of tBgpInstanceGRAdminState specifies the desired
         administrative state of the graceful restart capabilities for this
         instance of the BGP protocol.  When the value is 'outOfService' the
         graceful restart capabilities are disabled but the graceful restart
         configuration parameters are retained."
    DEFVAL      { inService }
    ::= { tBgpInstanceEntry 52 }

tBgpInstanceGROperState          OBJECT-TYPE
    SYNTAX      TmnxOperState
    MAX-ACCESS  read-only
    STATUS      current
    DESCRIPTION
        "The value of tBgpInstanceGROperState indicates the operational status
         of the graceful restart capabilities for this instance of the BGP
         protocol."
    ::= { tBgpInstanceEntry 53 }

tBgpInstanceVpnApplyImport       OBJECT-TYPE
    SYNTAX      TruthValue
    MAX-ACCESS  read-create
    STATUS      current
    DESCRIPTION
        "The value of tBgpInstanceVpnApplyImport specifies if the base instance
         BGP import route policies are applied to VPN-IPv4 routes.

         When the value is 'false'  the application of the base instance
         BGP import route policies to VPN-IPv4 routes is disabled."
    DEFVAL      { false }
    ::= { tBgpInstanceEntry 54 }

tBgpInstanceVpnApplyExport       OBJECT-TYPE
    SYNTAX      TruthValue
    MAX-ACCESS  read-create
    STATUS      current
    DESCRIPTION
        "The value of tBgpInstanceVpnApplyExport specifies if the base instance
         BGP export route policies are applied to VPN-IPv4 routes.

         When the value is 'false'  the application of the base instance
         BGP export route policies to VPN-IPv4 routes is disabled."
    DEFVAL      { false }
    ::= { tBgpInstanceEntry 55 }

tBgpInstanceIgpShortcut          OBJECT-TYPE
    SYNTAX      BITS {
        te       (0),
        ldp      (1),
        ip       (2),
        mpls     (3),
        mpls-bgp (4)
    }
    MAX-ACCESS  read-create
    STATUS      obsolete
    DESCRIPTION
        "The bits of tBgpInstanceIgpShortcut identify the Layer-2 tunneling
         mechanisms used for IGP shortcuts. If a bit is set, the corresponding
         tunneling mechanism will be used to resolve paths to BGP next-hops.

         The tunneling mechanisms represented by each bit are:
           te(0)  - RSVP Traffic Engineering
           ldp(1) - LDP /32 Route Forwarding Equivalence Class (FEC)
           ip(2)  - IP (IP-in-IP or GRE)
           mpls(3)- MPLS
           mpls-bgp(4)- MPLS with BGP label-route tunnel eligibility

         Evaluation of tunnel preference is based on the following order, in
         descending priority:
           1. Traffic Engineered Shortcut (RSVP-TE)
           2. LDP /32 Route FEC Shortcut
           3. IP Shortcut (IP-in-IP or GRE)
           4. Actual IGP Next-Hop.

         The 'mpls' option instructs BGP to first attempt to resolve the BGP
         next-hop to an RSVP LSP. If no RSVP LSP exists or the existing ones
         are down, BGP automatically searches for the LDP LSP with a FEC prefix
         corresponding to the same /32 prefix in the tunnel table and resolves
         the BGP next-hop to it.

         The 'mpls-bgp' option allows BGP to resolve the BGP next-hop using BGP
         tunnels in TTM, but the order of preference (which cannot be changed)
         is RSVP then LDP then BGP.

         This object was obsoleted in release 13.0."
    DEFVAL      { {} }
    ::= { tBgpInstanceEntry 56 }

tBgpInstanceDisallowIgp          OBJECT-TYPE
    SYNTAX      TruthValue
    MAX-ACCESS  read-create
    STATUS      obsolete
    DESCRIPTION
        "The value of tBgpInstanceDisallowIgp specifies if IGP next-hop to the
         BGP next-hop is used as the next-hop of the last resort.

         A value of 'true', disallows the IGP next-hop to the BGP next-hop from
         being used as the next-hop of the last resort. This is used to prevent
         routing loops.

         A value of 'false' reverts the IGP shortcut next-hop evaluation
         process to the default of allowing IGP next-hops as the next-hop of
         the last resort.

         When the value of tBgpInstanceIgpShortcut is changed, the value of
         tBgpInstanceDisallowIgp is reset to its default value.

         An 'inconsistentValue' error is returned if an attempt is made to set
         this object to a non-default value when the value of object
         tBgpInstanceIgpShortcut is not set to non-default value.

         This object was obsoleted in release 13.0."
    DEFVAL      { false }
    ::= { tBgpInstanceEntry 57 }

tBgpInstanceOrf                  OBJECT-TYPE
    SYNTAX      TruthValue
    MAX-ACCESS  read-create
    STATUS      current
    DESCRIPTION
        "The value of tBgpInstanceOrf specifies if outbound route filtering
         capability is enabled or disabled for the BGP instance."
    DEFVAL      { false }
    ::= { tBgpInstanceEntry 58 }

tBgpInstanceExtCommsOrf          OBJECT-TYPE
    SYNTAX      TruthValue
    MAX-ACCESS  read-create
    STATUS      current
    DESCRIPTION
        "The value of tBgpInstanceExtCommsOrf specifies if outbound route
         filtering capability is based on extended communities for the BGP
         instance."
    DEFVAL      { false }
    ::= { tBgpInstanceEntry 59 }

tBgpInstanceExtCommsSendOrf      OBJECT-TYPE
    SYNTAX      TruthValue
    MAX-ACCESS  read-create
    STATUS      current
    DESCRIPTION
        "The value of tBgpInstanceExtCommsSendOrf specifies if outbound route
         filter advertisement to the neighbors in this BGP instance."
    DEFVAL      { false }
    ::= { tBgpInstanceEntry 60 }

tBgpInstanceExtCommsRecvOrf      OBJECT-TYPE
    SYNTAX      TruthValue
    MAX-ACCESS  read-create
    STATUS      current
    DESCRIPTION
        "The value of tBgpInstanceExtCommsRecvOrf specifies if outbound route
         filter for this BGP instance is accepted from the neighbors is
         enabled."
    DEFVAL      { false }
    ::= { tBgpInstanceEntry 61 }

tBgpInstanceAllowInterAsVpn      OBJECT-TYPE
    SYNTAX      TruthValue
    MAX-ACCESS  read-create
    STATUS      current
    DESCRIPTION
        "The value of tBgpInstanceAllowInterAsVpn specifies whether VPNs can
         exchange routes across autonomous system boundaries, providing model B
         connectivity.

         When the value is 'true', ASBRs can advertise VPRN routes to their
         peers in other autonomous systems, and when it is 'false', they
         cannot."
    DEFVAL      { false }
    ::= { tBgpInstanceEntry 62 }

tBgpInstancePurgeTimer           OBJECT-TYPE
    SYNTAX      Unsigned32 (1..60)
    UNITS       "minutes"
    MAX-ACCESS  read-create
    STATUS      current
    DESCRIPTION
        "The value of tBgpInstancePurgeTimer specifies the maximum time, in
         minutes, before stale routes are purged."
    DEFVAL      { 10 }
    ::= { tBgpInstanceEntry 63 }

tBgpInstanceLocalAS4Byte         OBJECT-TYPE
    SYNTAX      InetAutonomousSystemNumber
    MAX-ACCESS  read-create
    STATUS      current
    DESCRIPTION
        "The value of tBgpInstanceLocalAS4Byte specifies the autonomous system
         number to be advertised to this peer."
    DEFVAL      { 0 }
    ::= { tBgpInstanceEntry 64 }

tBgpInstanceConfederationAS4Byte OBJECT-TYPE
    SYNTAX      InetAutonomousSystemNumber
    MAX-ACCESS  read-only
    STATUS      current
    DESCRIPTION
        "The value of tBgpInstanceConfederationAS4Byte indicates the
         confederation AS for this BGP instance. A value of zero indicates that
         no confederation AS has been assigned."
    ::= { tBgpInstanceEntry 65 }

tBgpInstanceDisable4ByteASN      OBJECT-TYPE
    SYNTAX      TruthValue
    MAX-ACCESS  read-create
    STATUS      current
    DESCRIPTION
        "The value of tBgpInstanceDisable4ByteASN specifies whether or not
         4-byte ASN capability will be advertised by this peer.

         When the value of tBgpInstanceDisable4ByteASN is set to false, 4-byte
         ASN support will be negotiated with the associated remote peers. When
         the value of tBgpInstanceDisable4ByteASN is set to true, 4-byte ASN
         capability will not be advertised by this peer."
    DEFVAL      { false }
    ::= { tBgpInstanceEntry 66 }

tBgpInstanceMultipathEiBgpState  OBJECT-TYPE
    SYNTAX      TmnxEnabledDisabled
    MAX-ACCESS  read-create
    STATUS      current
    DESCRIPTION
        "The value of tBgpInstanceMultipathEiBgpState specifies whether eiBGP
         load balancing is enabled or not. When the value of this object is set
         to 'enabled', eiBGP load balancing is enabled which allows the routes
         to be sent through multiple paths using iBGP or eBGP paths."
    DEFVAL      { disabled }
    ::= { tBgpInstanceEntry 67 }

tBgpInstanceHoldTimeIsStrict     OBJECT-TYPE
    SYNTAX      TruthValue
    MAX-ACCESS  read-create
    STATUS      obsolete
    DESCRIPTION
        "The value of tBgpInstanceHoldTimeIsStrict specifies whether or not
         tBgpInstanceHoldTime has to be strictly enforced.

         When the value of tBgpInstanceHoldTimeIsStrict is true, BGP will not
         negotiate a hold time lower than the configured value for
         tBgpInstanceHoldTime.

         This object is obsoleted in release 10.0. Desired functionality of
         strict enforcement of hold time can be achieved by configuring the
         value of tBgpInstanceMinHoldTime."
    DEFVAL      { false }
    ::= { tBgpInstanceEntry 68 }

tBgpInstanceAsPathIgnoreFamily   OBJECT-TYPE
    SYNTAX      TmnxIpFamily
    MAX-ACCESS  read-create
    STATUS      current
    DESCRIPTION
        "The value of tBgpInstanceAsPathIgnoreFamily specifies address families
         for which the AS path is used to determine the best BGP route. If this
         option is present, the AS paths of incoming routes are not used in the
         route selection process for the given families.

         A 'vpnIpv4 (2)' address is a 12-byte value consisting of
         the 8-byte route distinguisher, RD, and the 4-byte ipv4 IP address
         prefix.  The RD must be unique within the scope of the VPRN.
         This allows the IP address prefixes within different VRFs to
         overlap.

         'ipv6 (3)', 'mcastIpv4 (4)', and 'l2vpn (6)' are multi-protocol
         extensions to BGP.

         'mcastIpv6 (16)' is part of multi-protocol extension to BGP.

         A 'vpnIpv6 (5)' address is a 24-byte value consisting of the 8-byte
         RD, and 16 bytes for the IPv6 address. When both IPv4 and IPv6 VPRN
         services are enabled, the PE router uses the same RD for both address
         families.

         A 'mvpnIpv4  (7)' address is variable size value consisting of the
         1-byte route type, 1-byte length and variable size route type specific.
         Route type defines encoding for the route type specific field. Length
         indicates the length in octets of the route type specific field."
    DEFVAL      { {} }
    ::= { tBgpInstanceEntry 69 }

tBgpInstanceRemovePrivateASLmtd  OBJECT-TYPE
    SYNTAX      TruthValue
    MAX-ACCESS  read-create
    STATUS      current
    DESCRIPTION
        "The value of tBgpInstanceRemovePrivateASLmtd specifies whether BGP
         will remove the private AS numbers.

         When the value of tBgpInstanceRemovePrivateASLmtd is true, BGP will
         remove private AS numbers from the AS Path."
    DEFVAL      { false }
    ::= { tBgpInstanceEntry 70 }

tBgpInstancePMTUDiscovery        OBJECT-TYPE
    SYNTAX      TruthValue
    MAX-ACCESS  read-create
    STATUS      current
    DESCRIPTION
        "The value of tBgpInstancePMTUDiscovery specifies whether path MTU
         discovery is enabled for this BGP instance.

         When the value is set to 'true', path MTU discovery is enabled for
         this BGP instance. When the value is set to 'false', path MTU
         discovery is disabled."
    DEFVAL      { false }
    ::= { tBgpInstanceEntry 71 }

tBgpInstanceDisableRtTblInstall  OBJECT-TYPE
    SYNTAX      TruthValue
    MAX-ACCESS  read-create
    STATUS      current
    DESCRIPTION
        "The value of tBgpInstanceDisableRtTblInstall specifies whether to
         disable the installation of all (labeled and unlabeled) IPv4 and IPv6
         BGP routes into RTM (Routing Table Manager) and the FIB (Forwarding
         Information Base) on the base router instance."
    DEFVAL      { false }
    ::= { tBgpInstanceEntry 72 }

tBgpInstanceNHResUseBgpRoutes    OBJECT-TYPE
    SYNTAX      TruthValue
    MAX-ACCESS  read-create
    STATUS      current
    DESCRIPTION
        "The value of tBgpInstanceNHResUseBgpRoutes specifies whether to use
         BGP routes to resolve BGP nexthop for IPv4 and IPv6 families on this
         router instance."
    DEFVAL      { false }
    ::= { tBgpInstanceEntry 73 }

tBgpInstanceEnableRRVpnFwding    OBJECT-TYPE
    SYNTAX      TruthValue
    MAX-ACCESS  read-create
    STATUS      current
    DESCRIPTION
        "The value of tBgpInstanceEnableRRVpnFwding specifies whether a
         route-reflector will resolve VPN-IPv4 and VPN-IPv6 routes.

         When tBgpInstanceEnableRRVpnFwding is set to 'true', the
         route-reflector will resolve VPN-IPv4 and VPN-IPv6 routes.

         When the value of tBgpInstanceEnableRRVpnFwding is 'true' and
         next-hop-self is set for the peer, the route-reflector will generate
         new labels for all the resolved VPN-IPv4 and VPN-IPv6 routes.

         When the value of tBgpInstanceEnableRRVpnFwding is set to 'false',
         route-reflector will not resolve the VPN-IPv4 and VPN-IPv6 routes."
    DEFVAL      { false }
    ::= { tBgpInstanceEntry 74 }

tBgpInstRteTargetTable           OBJECT-TYPE
    SYNTAX      SEQUENCE OF TBgpInstRteTargetEntry
    MAX-ACCESS  not-accessible
    STATUS      current
    DESCRIPTION
        "Information about the route targets to be accepted and advertised from
         or to all peers. If there are entries in this table for a specific
         tBgpInstanceIndex then only routes with one or more of the route
         targets, tBgpInstanceRouteTarget, are accepted or advertised. These
         route target entries are applied to all peers connected to the BGP
         instance specified by tBgpInstanceIndex.

         If there are no entries in this table for a specific tBgpInstanceIndex
         all routes are reflected irrespective of the route targets associated
         with a route."
    ::= { tBgpInstanceObjects 3 }

tBgpInstRteTargetEntry           OBJECT-TYPE
    SYNTAX      TBgpInstRteTargetEntry
    MAX-ACCESS  not-accessible
    STATUS      current
    DESCRIPTION
        "An entry (conceptual row) in the tBgpInstRteTargetTable. Each entry
         represents a route target to be accepted and advertised from or to all
         peers."
    INDEX       {
        tBgpInstanceIndex,
        IMPLIED tBgpInstanceRouteTarget
    }
    ::= { tBgpInstRteTargetTable 1 }

TBgpInstRteTargetEntry           ::= SEQUENCE
{
    tBgpInstanceRouteTarget          TNamedItem,
    tBgpInstRteTargetRowStatus       RowStatus
}

tBgpInstanceRouteTarget          OBJECT-TYPE
    SYNTAX      TNamedItem
    MAX-ACCESS  not-accessible
    STATUS      current
    DESCRIPTION
        "Index for the tBgpInstRteTargetTable.  The value of
         tBgpInstanceRouteTarget specifies the extended community
         name to be accepted by a Route Reflector Server or advertised by
         the router when reflecting any routes. I.e, it does not apply to
         routes that are not reflected by the router."
    ::= { tBgpInstRteTargetEntry 1 }

tBgpInstRteTargetRowStatus       OBJECT-TYPE
    SYNTAX      RowStatus
    MAX-ACCESS  read-create
    STATUS      current
    DESCRIPTION
        "Row status of this BGP Instance route target entry. A row cannot be
         created in this table if the tBgpInstanceIndex entry does not exist in
         the tBgpInstanceTable."
    ::= { tBgpInstRteTargetEntry 2 }

tBgp4PathAttrTable               OBJECT-TYPE
    SYNTAX      SEQUENCE OF TBgp4PathAttrEntry
    MAX-ACCESS  not-accessible
    STATUS      current
    DESCRIPTION
        "The Nokia SROS series BGP-4 Received Path Attribute Table contains
         information about paths to destination networks received from all BGP4
         peers and is an extension of the bgp4PathAttrTable in the BGP4-MIB."
    ::= { tBgpInstanceObjects 4 }

tBgp4PathAttrEntry               OBJECT-TYPE
    SYNTAX      TBgp4PathAttrEntry
    MAX-ACCESS  not-accessible
    STATUS      current
    DESCRIPTION
        "Information about a path to a network.  "
    INDEX       {
        tBgpInstanceIndex,
        tBgp4PathAttrRD,
        bgp4PathAttrIpAddrPrefix,
        bgp4PathAttrIpAddrPrefixLen,
        bgp4PathAttrPeer
    }
    ::= { tBgp4PathAttrTable 1 }

TBgp4PathAttrEntry               ::= SEQUENCE
{
    tBgp4PathAttrRD                  TmnxVPNRouteDistinguisher,
    tBgp4PathAttrOriginID            IpAddress,
    tBgp4PathAttrClusterList         OCTET STRING,
    tBgp4PathAttrCommunity           OCTET STRING,
    tBgp4PathAttrExtCommunity        OCTET STRING,
    tbgp4PathAttrASPathSegment       OCTET STRING,
    tbgp4PathAttrAggregatorAS        InetAutonomousSystemNumber
}

tBgp4PathAttrRD                  OBJECT-TYPE
    SYNTAX      TmnxVPNRouteDistinguisher
    MAX-ACCESS  not-accessible
    STATUS      current
    DESCRIPTION
        "The value of tBgp4PathAttrRD specifies the Route Distinguisher
         associated with this BGP-4 path."
    ::= { tBgp4PathAttrEntry 1 }

tBgp4PathAttrOriginID            OBJECT-TYPE
    SYNTAX      IpAddress
    MAX-ACCESS  read-only
    STATUS      current
    DESCRIPTION
        "The value of tBgp4PathAttrOriginID indicates the Originator ID
         associated with this BGP-4 path that is used in route reflectors to
         specify the origin of the reflection."
    ::= { tBgp4PathAttrEntry 2 }

tBgp4PathAttrClusterList         OBJECT-TYPE
    SYNTAX      OCTET STRING (SIZE (1..257))
    MAX-ACCESS  read-only
    STATUS      current
    DESCRIPTION
        "The value of tBgp4PathAttrClusterList indicates the list of
         routers in the cluster associated with this BGP-4 path.  The first
         octet indicates the number of router IDs in the list.  The list
         is a sequence of 4-octet router IDs."
    ::= { tBgp4PathAttrEntry 3 }

tBgp4PathAttrCommunity           OBJECT-TYPE
    SYNTAX      OCTET STRING (SIZE (1..257))
    MAX-ACCESS  read-only
    STATUS      current
    DESCRIPTION
        "The value of tBgp4PathAttrCommunity indicates the list of route
         policy communities associated with this BGP-4 path.  The first
         octet indicates the number of communities in the list.  The list
         is a sequence of 4-octet communities."
    ::= { tBgp4PathAttrEntry 4 }

tBgp4PathAttrExtCommunity        OBJECT-TYPE
    SYNTAX      OCTET STRING (SIZE (1..257))
    MAX-ACCESS  read-only
    STATUS      current
    DESCRIPTION
        "The value of tBgp4PathAttrExtCommunity indicates the list of
         extended communities to be accepted by a Route Reflector Server
         associated with this BGP-4 path.  The first octet indicates the
         number of extended communities in the list.  The list is a
         sequence of extended communities.  The extended community is
         an 8-octet value similar to a route distinguisher."
    ::= { tBgp4PathAttrEntry 5 }

tbgp4PathAttrASPathSegment       OBJECT-TYPE
    SYNTAX      OCTET STRING (SIZE (0..255))
    MAX-ACCESS  read-only
    STATUS      current
    DESCRIPTION
        "The value of tbgp4PathAttrASPathSegment indicates the sequence of
         Autonomous System (AS) path segments.  Each AS path segment is
         represented by a triple <type, length, value>.

         The type is a 1-octet field which has two possible values:
              1      AS_SET: unordered set of ASs a route in the
                             UPDATE message has traversed
              2      AS_SEQUENCE: ordered set of ASs a route in the
                                  UPDATE message has traversed.

         The length is a 1-octet field containing the number of ASs in the
         value field.

         The value field contains one or more 4-byte AS numbers. Each AS is
         represented in the octet string as four octets."
    ::= { tBgp4PathAttrEntry 6 }

tbgp4PathAttrAggregatorAS        OBJECT-TYPE
    SYNTAX      InetAutonomousSystemNumber
    MAX-ACCESS  read-only
    STATUS      current
    DESCRIPTION
        "The value of tbgp4PathAttrAggregatorAS indicates the AS number of
         the last BGP4 speaker that performed route aggregation.  A value of
         zero (0) indicates the absence of this attribute."
    ::= { tBgp4PathAttrEntry 7 }

tBgpSendOrfRouteTargetTable      OBJECT-TYPE
    SYNTAX      SEQUENCE OF TBgpSendOrfRouteTargetEntry
    MAX-ACCESS  not-accessible
    STATUS      current
    DESCRIPTION
        "Information about the route targets to be advertised to the peers if
         it is Outbound route filtering capable."
    ::= { tBgpInstanceObjects 5 }

tBgpSendOrfRouteTargetEntry      OBJECT-TYPE
    SYNTAX      TBgpSendOrfRouteTargetEntry
    MAX-ACCESS  not-accessible
    STATUS      current
    DESCRIPTION
        "An entry in the tBgpSendOrfRouteTargetTable. Each entry represents a
         route target to be advertised to the peer."
    INDEX       {
        tBgpInstanceIndex,
        IMPLIED tBgpSendOrfRouteTarget
    }
    ::= { tBgpSendOrfRouteTargetTable 1 }

TBgpSendOrfRouteTargetEntry      ::= SEQUENCE
{
    tBgpSendOrfRouteTarget           TNamedItem,
    tBgpSendOrfRTRowStatus           RowStatus
}

tBgpSendOrfRouteTarget           OBJECT-TYPE
    SYNTAX      TNamedItem
    MAX-ACCESS  not-accessible
    STATUS      current
    DESCRIPTION
        "Index for the tBgpSendOrfRouteTargetTable. The value of
         tBgpSendOrfRouteTarget specifies the extended community name to be
         advertised to the peer."
    ::= { tBgpSendOrfRouteTargetEntry 1 }

tBgpSendOrfRTRowStatus           OBJECT-TYPE
    SYNTAX      RowStatus
    MAX-ACCESS  read-create
    STATUS      current
    DESCRIPTION
        "RowStatus for the Send Orf Route target entry."
    ::= { tBgpSendOrfRouteTargetEntry 2 }

tBgpInstanceParamsTable          OBJECT-TYPE
    SYNTAX      SEQUENCE OF TBgpInstanceParamsEntry
    MAX-ACCESS  not-accessible
    STATUS      current
    DESCRIPTION
        "Information about the attributes configured  for the BGP instance."
    ::= { tBgpInstanceObjects 6 }

tBgpInstanceParamsEntry          OBJECT-TYPE
    SYNTAX      TBgpInstanceParamsEntry
    MAX-ACCESS  not-accessible
    STATUS      current
    DESCRIPTION
        "An entry in the tBgpInstanceParamsTable. Each entry maintains the
         attributes configured for BGP instance."
    AUGMENTS    { tBgpInstanceEntry }
    ::= { tBgpInstanceParamsTable 1 }

TBgpInstanceParamsEntry          ::= SEQUENCE
{
    tBgpInstanceDisableFEFailover    TruthValue,
    tBgpInstanceDisableComms         TruthValue,
    tBgpInstanceDisableExtComms      TruthValue,
    tBgpInstanceDefaultOriginate     TmnxIpFamily,
    tBgpInstanceAdvertiseInactiveRts TruthValue,
    tBgpInstancePeerTracking         TruthValue,
    tBgpInstanceAuthKeyChain         TNamedItemOrEmpty,
    tBgpInstanceRapidWithdrawal      TruthValue,
    tBgpInstanceBfdEnabled           TruthValue,
    tBgpInstanceRapidUpdate          TmnxIpFamily,
    tBgpInstanceEnableAddPath        TruthValue,
    tBgpInstanceRecvAddPath          TmnxAddPathAddressFamily,
    tBgpInstanceIpv4AddPathLimit     TmnxAddPathSendLimit,
    tBgpInstanceVpnIpv4AddPathLimit  TmnxAddPathSendLimit,
    tBgpInstanceIpv6AddPathLimit     TmnxAddPathSendLimit,
    tBgpInstanceVpnIpv6AddPathLimit  TmnxAddPathSendLimit,
    tBgpInstanceTransportTunnel      BITS,
    tBgpInstanceFlowspecValidate     TruthValue,
    tBgpInstanceAdvertiseExternal    TmnxIpFamily,
    tBgpInstanceBackupPath           TmnxIpFamily,
    tBgpInstanceIgnoreNextHopMetric  TruthValue,
    tBgpInstanceMpBgpKeep            TruthValue,
    tBgpInstanceIgnoreRouterId       TruthValue,
    tBgpInstanceAlwaysCompMEDStrict  TruthValue,
    tBgpInstanceMinHoldTime          BgpHoldTime,
    tBgpInstRemovePrivateSkipPeerAs  TruthValue,
    tBgpInstLocalASNoPrependGlobalAS TruthValue,
    tBgpInstanceNHResPolicy          TLPolicyStatementNameOrEmpty,
    tBgpInstancePeerTrackingPolicy   TLPolicyStatementNameOrEmpty,
    tBgpInstGrRestartNotification    TruthValue,
    tBgpInstanceFaultTolerance       TruthValue,
    tBgpInstanceDampPeerOscillations TruthValue,
    tBgpInstDmpPeerOscInitialWaitTim Unsigned32,
    tBgpInstDmpPeerOscSecondWaitTime Unsigned32,
    tBgpInstDmpPeerOscMaxWaitTime    Unsigned32,
    tBgpInstDmpPeerOscErrorInterval  Unsigned32,
    tBgpInstanceDeterministicMED     TruthValue,
    tBgpInstanceSplitHorizon         TruthValue,
    tBgpInstMvpnVrfImportSubTypeNew  TruthValue,
    tBgpInstResolveLabelRoutesInRtm  TruthValue,
    tBgpInstanceCompOriginValidState TruthValue,
    tBgpInstanceThirdPartyNextHop    TruthValue,
    tBgpInstanceOrigInvalidUnusable  TruthValue,
    tBgpInstanceIgnoreRtrIdInternal  TmnxIpFamily,
    tBgpInstanceIgnoreRtrIdExternal  TmnxIpFamily,
    tBgpInstanceDynamicPeerLimit     Unsigned32,
    tBgpInstanceOverrideTunnelElc    TruthValue,
    tBgpInstanceEbgpIbgpEqual        TmnxIpFamily,
    tBgpInstanceLblIpv4AddPathLimit  TmnxAddPathSendLimit,
    tBgpInstanceLblIpv6AddPathLimit  TmnxAddPathSendLimit,
    tBgpInstanceLabelPreference      TmnxBgpPreference,
    tBgpInstanceLinkStateExEnable    TruthValue,
    tBgpInstanceLinkStateImEnable    TruthValue,
    tBgpInstanceDefRxEvpnEncap       INTEGER,
    tBgpInstanceNHResolveAllowStatic TruthValue,
    tBgpInstanceORRLocation          Unsigned32,
    tBgpInstanceORRAllowLocalFallbk  TruthValue,
    tBgpInstanceWeightedEcmp         TruthValue,
    tBgpInstanceFSValidateDestPfx    TruthValue,
    tBgpInstanceFSValidateRedirectIP TruthValue
}

tBgpInstanceDisableFEFailover    OBJECT-TYPE
    SYNTAX      TruthValue
    MAX-ACCESS  read-create
    STATUS      current
    DESCRIPTION
        "The value of tBgpInstanceDisableFEFailover specifies whether the
         router should drop an external BGP session immediately when the local
         interface goes down, or whether the BGP session should be kept up
         until the holdtime expires.

         Setting the value to 'true' causes the external BGP session to go down
         immediately when the local interface goes down."
    DEFVAL      { false }
    ::= { tBgpInstanceParamsEntry 1 }

tBgpInstanceDisableComms         OBJECT-TYPE
    SYNTAX      TruthValue
    MAX-ACCESS  read-create
    STATUS      current
    DESCRIPTION
        "The value of tBgpInstanceDisableComms enables or disables sending of
         community attribute to the peer for non-external communities."
    DEFVAL      { false }
    ::= { tBgpInstanceParamsEntry 2 }

tBgpInstanceDisableExtComms      OBJECT-TYPE
    SYNTAX      TruthValue
    MAX-ACCESS  read-create
    STATUS      current
    DESCRIPTION
        "The value of tBgpInstanceDisableExtComms enables or disables sending
         of community attribute to the peers for external communities."
    DEFVAL      { false }
    ::= { tBgpInstanceParamsEntry 3 }

tBgpInstanceDefaultOriginate     OBJECT-TYPE
    SYNTAX      TmnxIpFamily
    MAX-ACCESS  read-create
    STATUS      current
    DESCRIPTION
        "The value of tBgpInstanceDefaultOriginate specifies the types of
         AFI/SAFI for which SROS BGP will originate default route independent
         of the RTM default route"
    ::= { tBgpInstanceParamsEntry 4 }

tBgpInstanceAdvertiseInactiveRts OBJECT-TYPE
    SYNTAX      TruthValue
    MAX-ACCESS  read-create
    STATUS      current
    DESCRIPTION
        "The value of tBgpInstanceAdvertiseInactiveRts enables or disables
         advertising of inactive BGP routes to other BGP peers."
    DEFVAL      { false }
    ::= { tBgpInstanceParamsEntry 5 }

tBgpInstancePeerTracking         OBJECT-TYPE
    SYNTAX      TruthValue
    MAX-ACCESS  read-create
    STATUS      current
    DESCRIPTION
        "The value of tBgpInstancePeerTracking specifies whether tracking of
         BGP peers is enabled.

         A value of 'false' indicates that bgp peer tracking is disabled."
    DEFVAL      { false }
    ::= { tBgpInstanceParamsEntry 6 }

tBgpInstanceAuthKeyChain         OBJECT-TYPE
    SYNTAX      TNamedItemOrEmpty
    MAX-ACCESS  read-create
    STATUS      current
    DESCRIPTION
        "The value of tBgpInstanceAuthKeyChain specifies the
         keychain which will be used to sign and/or authenticate  the BGP
         protocol stream.

         The keychain name is defined by tmnxKeyChainName and is the index for
         TIMETRA-SECURITY-MIB::tmnxKeyChainTable"
    DEFVAL      { "" }
    ::= { tBgpInstanceParamsEntry 7 }

tBgpInstanceRapidWithdrawal      OBJECT-TYPE
    SYNTAX      TruthValue
    MAX-ACCESS  read-create
    STATUS      current
    DESCRIPTION
        "The value of tBgpInstanceRapidWithdrawal specifies whether the
         delay (minimum route advertisement) on sending BGP withdrawals has to
         be disabled.  Normal route withdrawals may be delayed up to the minimum
         route advertisement to allow for efficient packing of BGP updates.

         When the value of tBgpInstanceRapidWithdrawal is 'true' the delay on
         sending BGP withdrawals is disabled.  By default, the delay exists,
         which is the normal behavior for rapid withdrawal processing."
    DEFVAL      { false }
    ::= { tBgpInstanceParamsEntry 8 }

tBgpInstanceBfdEnabled           OBJECT-TYPE
    SYNTAX      TruthValue
    MAX-ACCESS  read-create
    STATUS      current
    DESCRIPTION
        "The value of tBgpInstanceBfdEnabled specifies whether Bi-directional
         Forwarding Detection is enabled on this router.

         When the value is 'true', BFD sessions can be established and BFD can
         be used as a signalling mechanism."
    DEFVAL      { false }
    ::= { tBgpInstanceParamsEntry 9 }

tBgpInstanceRapidUpdate          OBJECT-TYPE
    SYNTAX      TmnxIpFamily
    MAX-ACCESS  read-create
    STATUS      current
    DESCRIPTION
        "The value of tBgpInstanceRapidUpdate specifies the address families
         for which the BGP rapid updates will be sent to improve join/prune
         latency.

         tBgpInstanceRapidUpdate is supported for the following families:
         vpnIpv4      (2)
         vpnIpv6      (5)
         l2vpn        (6)
         mvpnIpv4     (7)
         mdtSafi      (8)
         mcastVpnIpv4 (12)
         mvpnIpv6     (13)
         evpn         (15)
         labelIpv4    (17)
         labelIpv6    (18)
         mcastVpnIpv6 (20)"
    DEFVAL      { {} }
    ::= { tBgpInstanceParamsEntry 10 }

tBgpInstanceEnableAddPath        OBJECT-TYPE
    SYNTAX      TruthValue
    MAX-ACCESS  read-create
    STATUS      obsolete
    DESCRIPTION
        "The value of tBgpInstanceEnableAddPath specifies whether the BGP
         ADD-PATH send capability is enabled on this BGP instance.

         ADD-PATH allows a BGP router to advertise multiple distinct paths for
         the same prefix/NLRI(Network Layer Reachability Information). This
         capability provides a number of potential benefits like reduced
         routing churn, faster convergence, better loadsharing etc.

         When the value of tBgpInstanceEnableAddPath is set to 'true', the BGP
         ADD-PATH send limit objects tBgpInstanceIpv4AddPathLimit,
         tBgpInstanceVpnIpv4AddPathLimit, tBgpInstanceIpv6AddPathLimit and
         tBgpInstanceVpnIpv6AddPathLimit
           , tBgpInstanceLblIpv4AddPathLimit
           , tBgpInstanceLblIpv6AddPathLimit
         represent their assigned values.

         The default value of tBgpInstanceEnableAddPath is 'false', which means
         the ADD-PATH capability is disabled on this BGP instance and the
         values of the BGP ADD-PATH send limit objects are not valid."
    DEFVAL      { false }
    ::= { tBgpInstanceParamsEntry 11 }

tBgpInstanceRecvAddPath          OBJECT-TYPE
    SYNTAX      TmnxAddPathAddressFamily
    MAX-ACCESS  read-create
    STATUS      obsolete
    DESCRIPTION
        "The value of tBgpInstanceRecvAddPath specifies the address families
         which are enabled to receive BGP ADD-PATH.

         ADD-PATH allows a BGP router to receive multiple distinct paths for
         the same prefix/NLRI (Network Layer Reachability Information)."
    DEFVAL      { {none} }
    ::= { tBgpInstanceParamsEntry 12 }

tBgpInstanceIpv4AddPathLimit     OBJECT-TYPE
    SYNTAX      TmnxAddPathSendLimit
    MAX-ACCESS  read-create
    STATUS      obsolete
    DESCRIPTION
        "The value of tBgpInstanceIpv4AddPathLimit specifies the maximum number
         of paths per IPv4 prefix that can be advertised to ADD-PATH peers.

         An 'inconsistentValue' error is returned if an attempt is made to set
         this object to a value greater than tBgpInstanceMultipathBgp."
    DEFVAL      { 0 }
    ::= { tBgpInstanceParamsEntry 13 }

tBgpInstanceVpnIpv4AddPathLimit  OBJECT-TYPE
    SYNTAX      TmnxAddPathSendLimit
    MAX-ACCESS  read-create
    STATUS      obsolete
    DESCRIPTION
        "The value of tBgpInstanceVpnIpv4AddPathLimit specifies the maximum
         number of paths per VPN IPv4 prefix that can be advertised to ADD-PATH
         peers.

         An 'inconsistentValue' error is returned if an attempt is made to set
         this object to a value greater than tBgpInstanceMultipathBgp."
    DEFVAL      { 0 }
    ::= { tBgpInstanceParamsEntry 14 }

tBgpInstanceIpv6AddPathLimit     OBJECT-TYPE
    SYNTAX      TmnxAddPathSendLimit
    MAX-ACCESS  read-create
    STATUS      obsolete
    DESCRIPTION
        "The value of tBgpInstanceIpv6AddPathLimit specifies the maximum number
         of paths per IPv6 prefix that can be advertised to ADD-PATH peers.

         An 'inconsistentValue' error is returned if an attempt is made to set
         this object to a value greater than tBgpInstanceMultipathBgp."
    DEFVAL      { 0 }
    ::= { tBgpInstanceParamsEntry 15 }

tBgpInstanceVpnIpv6AddPathLimit  OBJECT-TYPE
    SYNTAX      TmnxAddPathSendLimit
    MAX-ACCESS  read-create
    STATUS      obsolete
    DESCRIPTION
        "The value of tBgpInstanceVpnIpv6AddPathLimit specifies the maximum
         number of paths per VPN IPv6 prefix that can be advertised to ADD-PATH
         peers.

         An 'inconsistentValue' error is returned if an attempt is made to set
         this object to a value greater than tBgpInstanceMultipathBgp."
    DEFVAL      { 0 }
    ::= { tBgpInstanceParamsEntry 16 }

tBgpInstanceTransportTunnel      OBJECT-TYPE
    SYNTAX      BITS {
        ldp     (0),
        rsvp-te (1),
        mpls    (2)
    }
    MAX-ACCESS  read-create
    STATUS      obsolete
    DESCRIPTION
        "The bits of tBgpInstanceTransportTunnel specify whether VPNs can
         exchange routes across autonomous system boundaries, providing model B
         connectivity. The 'no' form of the command disallows ASBRs to
         advertise VPRN routes to their peers in other autonomous systems. If a
         bit is set, the corresponding mechanism will be used to exchange
         routes.

         The mechanisms represented by each bit are:
           ldp(0)     - This allows LDP based LSPS to be used as transport from
                        the ASBR to local PE routers
           rsvp-te(1) - This allows RSVP-TE based LSPS to be used as transport
                        from the ASBR to local PE routers
           mpls(2)    - This allows both LDP and RSVP-TE to be used to resolve
                        the BGP nexthop for VPRN routes in an associated VPRN
                        instance.

         This object was obsoleted in release 13.0."
    DEFVAL      { {ldp} }
    ::= { tBgpInstanceParamsEntry 17 }

tBgpInstanceFlowspecValidate     OBJECT-TYPE
    SYNTAX      TruthValue
    MAX-ACCESS  read-create
    STATUS      obsolete
    DESCRIPTION
        "The value of tBgpInstanceFlowspecValidate specifies whether validation
         of received flow specification routes is enabled on this router.

         When the value of tBgpInstanceFlowspecValidate is 'true', the flow
         routes received from other peers are validated.

         The default value of tBgpInstanceFlowspecValidate is 'false', which
         means validation of received flow routes is disabled and all flow
         specification routes are considered valid."
    DEFVAL      { false }
    ::= { tBgpInstanceParamsEntry 18 }

tBgpInstanceAdvertiseExternal    OBJECT-TYPE
    SYNTAX      TmnxIpFamily
    MAX-ACCESS  read-create
    STATUS      current
    DESCRIPTION
        "The value of tBgpInstanceAdvertiseExternal specifies the address
         families which are enabled on this router instance to advertise the
         best external route to the destination even when its best overall
         route is an internal route.

         An 'inconsistentValue' error is returned if an attempt is made to set
         this object to a non-default value when the value of object
         tBgpInstanceDisableClientReflect is set to 'false'."
    ::= { tBgpInstanceParamsEntry 19 }

tBgpInstanceBackupPath           OBJECT-TYPE
    SYNTAX      TmnxIpFamily
    MAX-ACCESS  read-create
    STATUS      current
    DESCRIPTION
        "The value of tBgpInstanceBackupPath specifies the address families for
         which the computation and use of a backup path is enabled on this
         router instance."
    ::= { tBgpInstanceParamsEntry 20 }

tBgpInstanceIgnoreNextHopMetric  OBJECT-TYPE
    SYNTAX      TruthValue
    MAX-ACCESS  read-create
    STATUS      current
    DESCRIPTION
        "The value of tBgpInstanceIgnoreNextHopMetric specifies whether
         next-hop metric should be ignored when computing best routes to a
         destination for the base router BGP instance."
    DEFVAL      { false }
    ::= { tBgpInstanceParamsEntry 21 }

tBgpInstanceMpBgpKeep            OBJECT-TYPE
    SYNTAX      TruthValue
    MAX-ACCESS  read-create
    STATUS      current
    DESCRIPTION
        "The value of tBgpInstanceMpBgpKeep specifies whether to maintain
         descriptive information for all Multiprotocol BGP (MP-BGP) routes on
         this BGP router instance regardless of the existing VPRN route
         policies currently configured."
    DEFVAL      { false }
    ::= { tBgpInstanceParamsEntry 22 }

tBgpInstanceIgnoreRouterId       OBJECT-TYPE
    SYNTAX      TruthValue
    MAX-ACCESS  read-create
    STATUS      current
    DESCRIPTION
        "The value of tBgpInstanceIgnoreRouterId specifies whether to ignore
         the BGP identifier (router-ID) comparison when comparing two paths
         learned from different EBGP neighbors as long as both paths are not
         from a configured-BGP peer.

         The router-ID comparison is ignored for routes from external BGP peers
         with family types corresponding to the bits set in the object
         tBgpInstanceIgnoreRtrIdExternal.

         The router-ID comparison is ignored for routes from internal BGP peers
         with family types corresponding to the bits set in the object
         tBgpInstanceIgnoreRtrIdInternal. The default value of
         tBgpInstanceIgnoreRouterId is 'false', which means the router-ID
         comparison is never ignored."
    DEFVAL      { false }
    ::= { tBgpInstanceParamsEntry 23 }

tBgpInstanceAlwaysCompMEDStrict  OBJECT-TYPE
    SYNTAX      TruthValue
    MAX-ACCESS  read-create
    STATUS      current
    DESCRIPTION
        "The state of tBgpInstanceAlwaysCompMEDStrict specifies whether to
         compare Multi-Exit Discriminator (MED) path attribute between routes
         learned from the same neighboring autonomous system (neighbor-AS) in
         the route selection process.

         When the state of tBgpInstanceAlwaysCompMEDStrict is set to 'true' it
         specifies that the MED value should be only compared between routes
         learned from same autonomous systems and if one of the route has no
         MED it should be assigned the lowest possible value of 'zero'.

         When the value of tBgpInstanceAlwaysCompareMED is 'infinity' and the
         state of tBgpInstanceAlwaysCompMEDStrict is set to 'true', the MED
         attribute of two routes is compared if they come from the same
         neighbor-AS and the routes are compared as though the route with the
         missing MED has a MED of infinity (the worst possible value, 2^32
         -1.)."
    DEFVAL      { true }
    ::= { tBgpInstanceParamsEntry 24 }

tBgpInstanceMinHoldTime          OBJECT-TYPE
    SYNTAX      BgpHoldTime
    MAX-ACCESS  read-create
    STATUS      current
    DESCRIPTION
        "The value of tBgpInstanceMinHoldTime specifies the minimum hold time
         that should be strictly enforced on tBgpInstanceHoldTime.

         When the value of tBgpInstanceMinHoldTime is configured, BGP will not
         negotiate a hold time lower than the configured value.

         An 'inconsistentValue' error is returned if an attempt is made to set
         this object to a value greater than tBgpInstanceHoldTime."
    DEFVAL      { 0 }
    ::= { tBgpInstanceParamsEntry 25 }

tBgpInstRemovePrivateSkipPeerAs  OBJECT-TYPE
    SYNTAX      TruthValue
    MAX-ACCESS  read-create
    STATUS      current
    DESCRIPTION
        "The value of tBgpInstRemovePrivateSkipPeerAs specifies whether or not
         to remove the private autonomous system number (ASN) from AS-Path, if
         the AS-Path contains the ASN of the external BGP (eBGP) neighbor on
         this BGP instance.

         When the value of tBgpInstRemovePrivateSkipPeerAs is true, BGP will
         not remove the private ASN from the AS-Path if it is the same
         autonomous system number as the remote eBGP peer."
    DEFVAL      { false }
    ::= { tBgpInstanceParamsEntry 26 }

tBgpInstLocalASNoPrependGlobalAS OBJECT-TYPE
    SYNTAX      TruthValue
    MAX-ACCESS  read-create
    STATUS      current
    DESCRIPTION
        "The value of tBgpInstLocalASNoPrependGlobalAS specifies whether or not
         to prepend the global-AS when advertising routes to the external BGP
         (eBGP) neighbor on this BGP instance.

         When the value of tBgpInstLocalASNoPrependGlobalAS is true, BGP will
         prepend only the local-AS to the AS_PATH of received routes from the
         remote eBGP peer.

         When the value of tBgpInstanceLocalAS4Byte is changed, the value of
         tBgpInstLocalASNoPrependGlobalAS is reset to its default value.

         An 'inconsistentValue' error is returned if an attempt is made to set
         this object to a non-default value when the value of object
         tBgpInstanceLocalAS4Byte is not set to non-default value."
    DEFVAL      { false }
    ::= { tBgpInstanceParamsEntry 27 }

tBgpInstanceNHResPolicy          OBJECT-TYPE
    SYNTAX      TLPolicyStatementNameOrEmpty
    MAX-ACCESS  read-create
    STATUS      current
    DESCRIPTION
        "The value of tBgpInstanceNHResPolicy specifies the policy to be
         applied for filtering the routes to be considered for next-hop
         resolution process."
    DEFVAL      { "" }
    ::= { tBgpInstanceParamsEntry 28 }

tBgpInstancePeerTrackingPolicy   OBJECT-TYPE
    SYNTAX      TLPolicyStatementNameOrEmpty
    MAX-ACCESS  read-create
    STATUS      current
    DESCRIPTION
        "The value of tBgpInstancePeerTrackingPolicy specifies the policy to be
         applied for BGP peer tracking on this router instance."
    DEFVAL      { "" }
    ::= { tBgpInstanceParamsEntry 29 }

tBgpInstGrRestartNotification    OBJECT-TYPE
    SYNTAX      TruthValue
    MAX-ACCESS  read-create
    STATUS      current
    DESCRIPTION
        "The value of tBgpInstGrRestartNotification specifies whether or not to
         perform Graceful Restart procedures after sending or receiving a
         NOTIFICATION message.

         When the value of tBgpInstGrRestartNotification is true, BGP will
         perform Graceful Restart procedures after sending or receiving a
         NOTIFICATION message."
    DEFVAL      { false }
    ::= { tBgpInstanceParamsEntry 30 }

tBgpInstanceFaultTolerance       OBJECT-TYPE
    SYNTAX      TruthValue
    MAX-ACCESS  read-create
    STATUS      current
    DESCRIPTION
        "The value of tBgpInstanceFaultTolerance specifies whether or not
         approaches like 'treat-as-withdraw' and other similar non-disruptive
         approaches can be used for handling a wide range of UPDATE message
         errors.

         A value of 'false' indicates that bgp fault-tolerance is disabled."
    DEFVAL      { false }
    ::= { tBgpInstanceParamsEntry 31 }

tBgpInstanceDampPeerOscillations OBJECT-TYPE
    SYNTAX      TruthValue
    MAX-ACCESS  read-create
    STATUS      current
    DESCRIPTION
        "The value of tBgpInstanceDampPeerOscillations specifies whether
         damping peer oscillations is enabled for this BGP instance.

         When the value is set to 'true', damping peer oscillations is enabled
         for this BGP instance. When the value is set to 'false', damping peer
         oscillations is disabled."
    DEFVAL      { false }
    ::= { tBgpInstanceParamsEntry 32 }

tBgpInstDmpPeerOscInitialWaitTim OBJECT-TYPE
    SYNTAX      Unsigned32 (0..2048)
    UNITS       "minutes"
    MAX-ACCESS  read-create
    STATUS      current
    DESCRIPTION
        "The value of tBgpInstDmpPeerOscInitialWaitTim specifies the time in
         minutes, that a session remains in the idle-state after it has been
         stable for a while for this BGP instance.

         When the value of tBgpInstanceDampPeerOscillations is changed, the
         value of tBgpInstDmpPeerOscInitialWaitTim is reset to its default
         value.

         An 'inconsistentValue' error is returned if an attempt is made to set
         this object without setting tBgpInstanceDampPeerOscillations."
    DEFVAL      { 0 }
    ::= { tBgpInstanceParamsEntry 33 }

tBgpInstDmpPeerOscSecondWaitTime OBJECT-TYPE
    SYNTAX      Unsigned32 (1..2048)
    UNITS       "minutes"
    MAX-ACCESS  read-create
    STATUS      current
    DESCRIPTION
        "The value of tBgpInstDmpPeerOscSecondWaitTime specifies the time in
         minutes, that is doubled after each repeated session failure that
         occurs within a relatively short span of time for this BGP instance.

         When the value of tBgpInstanceDampPeerOscillations is changed, the
         value of tBgpInstDmpPeerOscSecondWaitTime is reset to its default
         value.

         An 'inconsistentValue' error is returned if an attempt is made to set
         this object without setting tBgpInstanceDampPeerOscillations."
    DEFVAL      { 5 }
    ::= { tBgpInstanceParamsEntry 34 }

tBgpInstDmpPeerOscMaxWaitTime    OBJECT-TYPE
    SYNTAX      Unsigned32 (1..2048)
    UNITS       "minutes"
    MAX-ACCESS  read-create
    STATUS      current
    DESCRIPTION
        "The value of tBgpInstDmpPeerOscMaxWaitTime specifies the maximum
         amount of time in minutes, that the session remains in the idle-state
         after it has experienced repeated instability for this BGP instance.

         When the value of tBgpInstanceDampPeerOscillations is changed, the
         value of tBgpInstDmpPeerOscMaxWaitTime is reset to its default value.

         An 'inconsistentValue' error is returned if an attempt is made to set
         this object without setting tBgpInstanceDampPeerOscillations."
    DEFVAL      { 60 }
    ::= { tBgpInstanceParamsEntry 35 }

tBgpInstDmpPeerOscErrorInterval  OBJECT-TYPE
    SYNTAX      Unsigned32 (0..2048)
    UNITS       "minutes"
    MAX-ACCESS  read-create
    STATUS      current
    DESCRIPTION
        "The value of tBgpInstDmpPeerOscErrorInterval specifies the time in
         minutes after a session reset, during which the session must be
         error-free in order to reset the penalty counter and return
         idle-hold-time to tBgpInstDmpPeerOscInitialWaitTim for this BGP
         instance.

         When the value of tBgpInstanceDampPeerOscillations is changed, the
         value of tBgpInstDmpPeerOscErrorInterval is reset to its default
         value.

         An 'inconsistentValue' error is returned if an attempt is made to set
         this object without setting tBgpInstanceDampPeerOscillations."
    DEFVAL      { 30 }
    ::= { tBgpInstanceParamsEntry 36 }

tBgpInstanceDeterministicMED     OBJECT-TYPE
    SYNTAX      TruthValue
    MAX-ACCESS  read-create
    STATUS      current
    DESCRIPTION
        "The value of tBgpInstanceDeterministicMED specifies whether
         deterministic MED is enabled for this BGP instance.

         When the value of tBgpInstanceDeterministicMED is 'true' the router
         will group all paths belonging to the same AS and compare them
         together before comparing them to paths from different ASes"
    DEFVAL      { false }
    ::= { tBgpInstanceParamsEntry 37 }

tBgpInstanceSplitHorizon         OBJECT-TYPE
    SYNTAX      TruthValue
    MAX-ACCESS  read-create
    STATUS      current
    DESCRIPTION
        "The value of tBgpInstanceSplitHorizon specifies whether or not the
         peers under this instance reflect the best route back to the peer from
         which the route was received.

         When the value of tBgpInstanceSplitHorizon is 'true', the peers under
         this instance will not reflect best routes to the peers from which the
         route was received."
    DEFVAL      { false }
    ::= { tBgpInstanceParamsEntry 38 }

tBgpInstMvpnVrfImportSubTypeNew  OBJECT-TYPE
    SYNTAX      TruthValue
    MAX-ACCESS  read-create
    STATUS      current
    DESCRIPTION
        "The value of tBgpInstMvpnVrfImportSubTypeNew specifies whether or not
         the MPVN VRF route import extended community is assigned the new IANA
         value of 0x010b or the old extended community type code of 0x010a.

         When the value of tBgpInstMvpnVrfImportSubTypeNew is 'true', the the
         subtype encoded in advertised routes is 0x010b.

         When the value of tBgpInstMvpnVrfImportSubTypeNew is 'false', the the
         subtype encoded in advertised routes is 0x010a."
    DEFVAL      { false }
    ::= { tBgpInstanceParamsEntry 39 }

tBgpInstResolveLabelRoutesInRtm  OBJECT-TYPE
    SYNTAX      TruthValue
    MAX-ACCESS  read-create
    STATUS      current
    DESCRIPTION
        "The value of tBgpInstResolveLabelRoutesInRtm specifies whether we can
         fall back to RTM resolution of the BGP next hop for labeled routes if
         the TTM resolution fails."
    DEFVAL      { false }
    ::= { tBgpInstanceParamsEntry 40 }

tBgpInstanceCompOriginValidState OBJECT-TYPE
    SYNTAX      TruthValue
    MAX-ACCESS  read-create
    STATUS      current
    DESCRIPTION
        "The value of tBgpInstanceCompOriginValidState specifies whether the
         origin validation state is used in the BGP decision process."
    DEFVAL      { false }
    ::= { tBgpInstanceParamsEntry 41 }

tBgpInstanceThirdPartyNextHop    OBJECT-TYPE
    SYNTAX      TruthValue
    MAX-ACCESS  read-create
    STATUS      current
    DESCRIPTION
        "The value of tBgpInstanceThirdPartyNextHop specifies if there is any
         third party next-hop processing done towards single-hop EBGP peers in
         this instance.

         When false, NEXT_HOP will always carry the IP address of the interface
         used to establish the TCP connection to the peer"
    DEFVAL      { false }
    ::= { tBgpInstanceParamsEntry 42 }

tBgpInstanceOrigInvalidUnusable  OBJECT-TYPE
    SYNTAX      TruthValue
    MAX-ACCESS  read-create
    STATUS      current
    DESCRIPTION
        "The value of tBgpInstanceOrigInvalidUnusable specifies whether to use
         or ignore the routes that have an origin validation state of
         'Invalid'.

         When the value of tBgpInstanceOrigInvalidUnusable is set to 'true',
         the routes that have an origin validation state of 'Invalid' are
         considered unusable.

         When the value of tBgpInstanceOrigInvalidUnusable is set to 'false',
         the routes that have an origin validation state of 'Invalid' are
         compared to other usable routes for the same prefix."
    DEFVAL      { false }
    ::= { tBgpInstanceParamsEntry 43 }

tBgpInstanceIgnoreRtrIdInternal  OBJECT-TYPE
    SYNTAX      TmnxIpFamily
    MAX-ACCESS  read-create
    STATUS      current
    DESCRIPTION
        "The value of tBgpInstanceIgnoreRtrIdInternal specifies the address
         families of the routes from internal BGP peers for which router-ID is
         ignored, during comparison of paths learned from them.

         An 'inconsistentValue' error is returned if an attempt is made to set
         this object when the value of tBgpInstanceIgnoreRouterId is 'false'."
    DEFVAL      { {} }
    ::= { tBgpInstanceParamsEntry 44 }

tBgpInstanceIgnoreRtrIdExternal  OBJECT-TYPE
    SYNTAX      TmnxIpFamily
    MAX-ACCESS  read-create
    STATUS      current
    DESCRIPTION
        "The value of tBgpInstanceIgnoreRtrIdExternal specifies the address
         families of the routes from external BGP peers for which router-ID is
         ignored, during comparison of paths learned from them.

         An 'inconsistentValue' error is returned if an attempt is made to set
         this object when the value of tBgpInstanceIgnoreRouterId is 'false'."
    DEFVAL      { {} }
    ::= { tBgpInstanceParamsEntry 45 }

tBgpInstanceDynamicPeerLimit     OBJECT-TYPE
    SYNTAX      Unsigned32 (0..8192)
    MAX-ACCESS  read-create
    STATUS      current
    DESCRIPTION
        "The value of tBgpInstanceDynamicPeerLimit specifies the value of
         dynamic peer limit for this BGP instance.

         If tBgpInstanceDynamicPeerLimit is set to zero (0), the dynamic peer
         limit is disabled for this BGP instance."
    DEFVAL      { 0 }
    ::= { tBgpInstanceParamsEntry 46 }

tBgpInstanceOverrideTunnelElc    OBJECT-TYPE
    SYNTAX      TruthValue
    MAX-ACCESS  read-create
    STATUS      current
    DESCRIPTION
        "When the value of tBgpInstanceOverrideTunnelElc is set to 'true', the
         system should assume that all far-ends for BGP tunnels are entropy
         label capable, irrespective of any received capability signaling."
    DEFVAL      { false }
    ::= { tBgpInstanceParamsEntry 50 }

tBgpInstanceEbgpIbgpEqual        OBJECT-TYPE
    SYNTAX      TmnxIpFamily
    MAX-ACCESS  read-create
    STATUS      current
    DESCRIPTION
        "The value of tBgpInstanceEbgpIbgpEqual specifies address families for
         which EBGP and IBGP learned paths are considered equal. If this option
         is present, ebgp-ibgp-equal affects the order of rib-in routes in a
         rib node. It can change the choice of the best path."
    DEFVAL      { {} }
    ::= { tBgpInstanceParamsEntry 51 }

tBgpInstanceLblIpv4AddPathLimit  OBJECT-TYPE
    SYNTAX      TmnxAddPathSendLimit
    MAX-ACCESS  read-create
    STATUS      obsolete
    DESCRIPTION
        "The value of tBgpInstanceLblIpv4AddPathLimit specifies the maximum
         number of paths per label IPv4 prefix that can be advertised to
         ADD-PATH peers.

         An 'inconsistentValue' error is returned if an attempt is made to set
         this object to a value greater than tBgpInstanceMultipathBgp."
    DEFVAL      { 0 }
    ::= { tBgpInstanceParamsEntry 52 }

tBgpInstanceLblIpv6AddPathLimit  OBJECT-TYPE
    SYNTAX      TmnxAddPathSendLimit
    MAX-ACCESS  read-create
    STATUS      obsolete
    DESCRIPTION
        "The value of tBgpInstanceLblIpv6AddPathLimit specifies the maximum
         number of paths per label IPv6 prefix that can be advertised to
         ADD-PATH peers.

         An 'inconsistentValue' error is returned if an attempt is made to set
         this object to a value greater than tBgpInstanceMultipathBgp."
    DEFVAL      { 0 }
    ::= { tBgpInstanceParamsEntry 53 }

tBgpInstanceLabelPreference      OBJECT-TYPE
    SYNTAX      TmnxBgpPreference (1..255)
    MAX-ACCESS  read-create
    STATUS      current
    DESCRIPTION
        "The value of tBgpInstanceLabelPreference specifies the route
         preference for label-IPv4 and label-IPv6 routes learned via the peer."
    DEFVAL      { 170 }
    ::= { tBgpInstanceParamsEntry 54 }

tBgpInstanceLinkStateExEnable    OBJECT-TYPE
    SYNTAX      TruthValue
    MAX-ACCESS  read-create
    STATUS      current
    DESCRIPTION
        "The value of tBgpInstanceLinkStateExEnable decides whether to export
         the TED database into BGP.

         If the value is set to 'true', then the BGP instance will allow export
         of TED NLRI updates.

         If the value is set to 'false', then the BGP instance will not export
         the TED NLRI updates."
    DEFVAL      { false }
    ::= { tBgpInstanceParamsEntry 55 }

tBgpInstanceLinkStateImEnable    OBJECT-TYPE
    SYNTAX      TruthValue
    MAX-ACCESS  read-create
    STATUS      current
    DESCRIPTION
        "The value of tBgpInstanceLinkStateImEnable decides whether to receive
         TED NLRI updates. It is only applicable to Virtual Service Router
         (VSR) running in Network Service Provider (NSP).

         If the value is set to 'true', then the BGP instance will import the
         TED NLRI updates.

         If the value is set to 'false', then the BGP instance will not import
         the TED NLRI updates."
    DEFVAL      { false }
    ::= { tBgpInstanceParamsEntry 56 }

tBgpInstanceDefRxEvpnEncap       OBJECT-TYPE
    SYNTAX      INTEGER {
        mpls  (0),
        vxlan (1)
    }
    MAX-ACCESS  read-create
    STATUS      current
    DESCRIPTION
        "The value of tBgpInstanceDefRxEvpnEncap specifies how BGP will treat a
         received EVPN route without BGP encapsulation extended community. If
         no encapsulation is received, BGP will validate the route as MPLS or
         VXLAN depending on the the value of tBgpInstanceDefRxEvpnEncap."
    DEFVAL      { mpls }
    ::= { tBgpInstanceParamsEntry 57 }

tBgpInstanceNHResolveAllowStatic OBJECT-TYPE
    SYNTAX      TruthValue
    MAX-ACCESS  read-create
    STATUS      current
    DESCRIPTION
        "The value of tBgpInstanceNHResolveAllowStatic specifies whether we can
         consider using regular static route for resolving routes for families
         VPN-IPv4, VPN-IPv6, Label-IPv4 and Label-IPv6."
    DEFVAL      { false }
    ::= { tBgpInstanceParamsEntry 58 }

tBgpInstanceORRLocation          OBJECT-TYPE
    SYNTAX      Unsigned32 (0..255)
    MAX-ACCESS  read-create
    STATUS      current
    DESCRIPTION
        "The value of tBgpInstanceORRLocation specifies the identifier of a
         location configured under optimal-route-reflection. The location is
         used to calculate the next-hop cost in the TE-DB and select the best
         path to advertise to the client of this route-reflector."
    DEFVAL      { 0 }
    ::= { tBgpInstanceParamsEntry 59 }

tBgpInstanceORRAllowLocalFallbk  OBJECT-TYPE
    SYNTAX      TruthValue
    MAX-ACCESS  read-create
    STATUS      current
    DESCRIPTION
        "The value of tBgpInstanceORRAllowLocalFallbk decides what the system
         should do when the BGP next-hop is not reachable in the TE-DB for the
         configured location, tBgpInstanceORRLocation.

         If the value is set to 'true', then next-hop cost calculation and
         best-path selection default back to the location of the
         route-reflector in the network.

         If the value is set to 'false', then no routes are advertised to the
         client(s)."
    DEFVAL      { false }
    ::= { tBgpInstanceParamsEntry 60 }

tBgpInstanceWeightedEcmp         OBJECT-TYPE
    SYNTAX      TruthValue
    MAX-ACCESS  read-create
    STATUS      current
    DESCRIPTION
        "The value of tBgpInstanceWeightedEcmp specifies that if weighted-ecmp
         is enabled, then ECMP is applied across LSPs to the same BGP next-hop,
         based on the configured load-balancing-weight of each LSP."
    DEFVAL      { false }
    ::= { tBgpInstanceParamsEntry 61 }

tBgpInstanceFSValidateDestPfx    OBJECT-TYPE
    SYNTAX      TruthValue
    MAX-ACCESS  read-create
    STATUS      current
    DESCRIPTION
        "The value of tBgpInstanceFSValidateDestPfx specifies whether
         validation of received flow specification routes is enabled on this
         router.

         When the value of tBgpInstanceFSValidateDestPfx is 'true', the flow
         routes received from other peers are validated.

         The default value of tBgpInstanceFSValidateDestPfx is 'false', which
         means validation of received flow routes is disabled and all flow
         specification routes are considered valid."
    DEFVAL      { false }
    ::= { tBgpInstanceParamsEntry 62 }

tBgpInstanceFSValidateRedirectIP OBJECT-TYPE
    SYNTAX      TruthValue
    MAX-ACCESS  read-create
    STATUS      current
    DESCRIPTION
        "The value of tBgpInstanceFSValidateRedirectIP specifies whether
         validation of flow specification routes received with a
         redirect-to-IPv4 extended community is enabled on this router. A flow
         specification route is considered valid if the origin AS in the
         AS_PATH and AS4_PATH attribute of the flow specification route matches
         the origin AS in the AS_PATH and AS4_PATH attribute of the best-match
         unicast route for the IPv4 address in the global administrator field
         of the extended community.

         When the value of tBgpInstanceFSValidateRedirectIP is 'true',
         validation of flow specification routes received with a
         redirect-to-IPv4 extended community is enabled.

         When the value of tBgpInstanceFSValidateRedirectIP is 'false',
         validation of flow specification routes received with a
         redirect-to-IPv4 extended community is disabled."
    DEFVAL      { false }
    ::= { tBgpInstanceParamsEntry 63 }

tBgpInstancePlcyTable            OBJECT-TYPE
    SYNTAX      SEQUENCE OF TBgpInstancePlcyEntry
    MAX-ACCESS  not-accessible
    STATUS      current
    DESCRIPTION
        "tBgpInstancePlcyTable consists of information about each running
         instance of BGP."
    ::= { tBgpInstanceObjects 7 }

tBgpInstancePlcyEntry            OBJECT-TYPE
    SYNTAX      TBgpInstancePlcyEntry
    MAX-ACCESS  not-accessible
    STATUS      current
    DESCRIPTION
        "An entry (conceptual row) in the tBgpInstancePlcyTable. Each entry
         represents an instance of BGP running on the virtual router."
    AUGMENTS    { tBgpInstanceEntry }
    ::= { tBgpInstancePlcyTable 1 }

TBgpInstancePlcyEntry            ::= SEQUENCE
{
    tBgpInstancePlcyImportPolicy1    TXLPolicyNameOrExpOrEmpty,
    tBgpInstancePlcyImportPolicy2    TLPolicyNameOrExpOrEmpty,
    tBgpInstancePlcyImportPolicy3    TLPolicyNameOrExpOrEmpty,
    tBgpInstancePlcyImportPolicy4    TLPolicyNameOrExpOrEmpty,
    tBgpInstancePlcyImportPolicy5    TLPolicyNameOrExpOrEmpty,
    tBgpInstancePlcyImportPolicy6    TLPolicyNameOrExpOrEmpty,
    tBgpInstancePlcyImportPolicy7    TLPolicyNameOrExpOrEmpty,
    tBgpInstancePlcyImportPolicy8    TLPolicyNameOrExpOrEmpty,
    tBgpInstancePlcyImportPolicy9    TLPolicyNameOrExpOrEmpty,
    tBgpInstancePlcyImportPolicy10   TLPolicyNameOrExpOrEmpty,
    tBgpInstancePlcyImportPolicy11   TLPolicyNameOrExpOrEmpty,
    tBgpInstancePlcyImportPolicy12   TLPolicyNameOrExpOrEmpty,
    tBgpInstancePlcyImportPolicy13   TLPolicyNameOrExpOrEmpty,
    tBgpInstancePlcyImportPolicy14   TLPolicyNameOrExpOrEmpty,
    tBgpInstancePlcyImportPolicy15   TLPolicyNameOrExpOrEmpty,
    tBgpInstancePlcyExportPolicy1    TXLPolicyNameOrExpOrEmpty,
    tBgpInstancePlcyExportPolicy2    TLPolicyNameOrExpOrEmpty,
    tBgpInstancePlcyExportPolicy3    TLPolicyNameOrExpOrEmpty,
    tBgpInstancePlcyExportPolicy4    TLPolicyNameOrExpOrEmpty,
    tBgpInstancePlcyExportPolicy5    TLPolicyNameOrExpOrEmpty,
    tBgpInstancePlcyExportPolicy6    TLPolicyNameOrExpOrEmpty,
    tBgpInstancePlcyExportPolicy7    TLPolicyNameOrExpOrEmpty,
    tBgpInstancePlcyExportPolicy8    TLPolicyNameOrExpOrEmpty,
    tBgpInstancePlcyExportPolicy9    TLPolicyNameOrExpOrEmpty,
    tBgpInstancePlcyExportPolicy10   TLPolicyNameOrExpOrEmpty,
    tBgpInstancePlcyExportPolicy11   TLPolicyNameOrExpOrEmpty,
    tBgpInstancePlcyExportPolicy12   TLPolicyNameOrExpOrEmpty,
    tBgpInstancePlcyExportPolicy13   TLPolicyNameOrExpOrEmpty,
    tBgpInstancePlcyExportPolicy14   TLPolicyNameOrExpOrEmpty,
    tBgpInstancePlcyExportPolicy15   TLPolicyNameOrExpOrEmpty
}

tBgpInstancePlcyImportPolicy1    OBJECT-TYPE
    SYNTAX      TXLPolicyNameOrExpOrEmpty
    MAX-ACCESS  read-create
    STATUS      current
    DESCRIPTION
        "The value of tBgpInstancePlcyImportPolicy1 specifies the first import
         policy."
    DEFVAL      { "" }
    ::= { tBgpInstancePlcyEntry 1 }

tBgpInstancePlcyImportPolicy2    OBJECT-TYPE
    SYNTAX      TLPolicyNameOrExpOrEmpty
    MAX-ACCESS  read-create
    STATUS      current
    DESCRIPTION
        "The value of tBgpInstancePlcyImportPolicy2 specifies the second import
         policy."
    DEFVAL      { "" }
    ::= { tBgpInstancePlcyEntry 2 }

tBgpInstancePlcyImportPolicy3    OBJECT-TYPE
    SYNTAX      TLPolicyNameOrExpOrEmpty
    MAX-ACCESS  read-create
    STATUS      current
    DESCRIPTION
        "The value of tBgpInstancePlcyImportPolicy3 specifies the third import
         policy."
    DEFVAL      { "" }
    ::= { tBgpInstancePlcyEntry 3 }

tBgpInstancePlcyImportPolicy4    OBJECT-TYPE
    SYNTAX      TLPolicyNameOrExpOrEmpty
    MAX-ACCESS  read-create
    STATUS      current
    DESCRIPTION
        "The value of tBgpInstancePlcyImportPolicy4 specifies the fourth import
         policy."
    DEFVAL      { "" }
    ::= { tBgpInstancePlcyEntry 4 }

tBgpInstancePlcyImportPolicy5    OBJECT-TYPE
    SYNTAX      TLPolicyNameOrExpOrEmpty
    MAX-ACCESS  read-create
    STATUS      current
    DESCRIPTION
        "The value of tBgpInstancePlcyImportPolicy5 specifies the fifth import
         policy."
    DEFVAL      { "" }
    ::= { tBgpInstancePlcyEntry 5 }

tBgpInstancePlcyImportPolicy6    OBJECT-TYPE
    SYNTAX      TLPolicyNameOrExpOrEmpty
    MAX-ACCESS  read-create
    STATUS      current
    DESCRIPTION
        "The value of tBgpInstancePlcyImportPolicy6 specifies the sixth import
         policy."
    DEFVAL      { "" }
    ::= { tBgpInstancePlcyEntry 6 }

tBgpInstancePlcyImportPolicy7    OBJECT-TYPE
    SYNTAX      TLPolicyNameOrExpOrEmpty
    MAX-ACCESS  read-create
    STATUS      current
    DESCRIPTION
        "The value of tBgpInstancePlcyImportPolicy7 specifies the seventh
         import policy."
    DEFVAL      { "" }
    ::= { tBgpInstancePlcyEntry 7 }

tBgpInstancePlcyImportPolicy8    OBJECT-TYPE
    SYNTAX      TLPolicyNameOrExpOrEmpty
    MAX-ACCESS  read-create
    STATUS      current
    DESCRIPTION
        "The value of tBgpInstancePlcyImportPolicy8 specifies the eighth import
         policy."
    DEFVAL      { "" }
    ::= { tBgpInstancePlcyEntry 8 }

tBgpInstancePlcyImportPolicy9    OBJECT-TYPE
    SYNTAX      TLPolicyNameOrExpOrEmpty
    MAX-ACCESS  read-create
    STATUS      current
    DESCRIPTION
        "The value of tBgpInstancePlcyImportPolicy9 specifies the ninth import
         policy."
    DEFVAL      { "" }
    ::= { tBgpInstancePlcyEntry 9 }

tBgpInstancePlcyImportPolicy10   OBJECT-TYPE
    SYNTAX      TLPolicyNameOrExpOrEmpty
    MAX-ACCESS  read-create
    STATUS      current
    DESCRIPTION
        "The value of tBgpInstancePlcyImportPolicy10 specifies the tenth import
         policy."
    DEFVAL      { "" }
    ::= { tBgpInstancePlcyEntry 10 }

tBgpInstancePlcyImportPolicy11   OBJECT-TYPE
    SYNTAX      TLPolicyNameOrExpOrEmpty
    MAX-ACCESS  read-create
    STATUS      current
    DESCRIPTION
        "The value of tBgpInstancePlcyImportPolicy11 specifies the eleventh
         import policy."
    DEFVAL      { "" }
    ::= { tBgpInstancePlcyEntry 11 }

tBgpInstancePlcyImportPolicy12   OBJECT-TYPE
    SYNTAX      TLPolicyNameOrExpOrEmpty
    MAX-ACCESS  read-create
    STATUS      current
    DESCRIPTION
        "The value of tBgpInstancePlcyImportPolicy12 specifies the twelfth
         import policy."
    DEFVAL      { "" }
    ::= { tBgpInstancePlcyEntry 12 }

tBgpInstancePlcyImportPolicy13   OBJECT-TYPE
    SYNTAX      TLPolicyNameOrExpOrEmpty
    MAX-ACCESS  read-create
    STATUS      current
    DESCRIPTION
        "The value of tBgpInstancePlcyImportPolicy13 specifies the thirteenth
         import policy."
    DEFVAL      { "" }
    ::= { tBgpInstancePlcyEntry 13 }

tBgpInstancePlcyImportPolicy14   OBJECT-TYPE
    SYNTAX      TLPolicyNameOrExpOrEmpty
    MAX-ACCESS  read-create
    STATUS      current
    DESCRIPTION
        "The value of tBgpInstancePlcyImportPolicy14 specifies the fourteenth
         import policy."
    DEFVAL      { "" }
    ::= { tBgpInstancePlcyEntry 14 }

tBgpInstancePlcyImportPolicy15   OBJECT-TYPE
    SYNTAX      TLPolicyNameOrExpOrEmpty
    MAX-ACCESS  read-create
    STATUS      current
    DESCRIPTION
        "The value of tBgpInstancePlcyImportPolicy15 specifies the fifteenth
         import policy."
    DEFVAL      { "" }
    ::= { tBgpInstancePlcyEntry 15 }

tBgpInstancePlcyExportPolicy1    OBJECT-TYPE
    SYNTAX      TXLPolicyNameOrExpOrEmpty
    MAX-ACCESS  read-create
    STATUS      current
    DESCRIPTION
        "The value of tBgpInstancePlcyExportPolicy1 specifies the first export
         policy."
    DEFVAL      { "" }
    ::= { tBgpInstancePlcyEntry 16 }

tBgpInstancePlcyExportPolicy2    OBJECT-TYPE
    SYNTAX      TLPolicyNameOrExpOrEmpty
    MAX-ACCESS  read-create
    STATUS      current
    DESCRIPTION
        "The value of tBgpInstancePlcyExportPolicy2 specifies the second export
         policy."
    DEFVAL      { "" }
    ::= { tBgpInstancePlcyEntry 17 }

tBgpInstancePlcyExportPolicy3    OBJECT-TYPE
    SYNTAX      TLPolicyNameOrExpOrEmpty
    MAX-ACCESS  read-create
    STATUS      current
    DESCRIPTION
        "The value of tBgpInstancePlcyExportPolicy3 specifies the third export
         policy."
    DEFVAL      { "" }
    ::= { tBgpInstancePlcyEntry 18 }

tBgpInstancePlcyExportPolicy4    OBJECT-TYPE
    SYNTAX      TLPolicyNameOrExpOrEmpty
    MAX-ACCESS  read-create
    STATUS      current
    DESCRIPTION
        "The value of tBgpInstancePlcyExportPolicy4 specifies the fourth export
         policy."
    DEFVAL      { "" }
    ::= { tBgpInstancePlcyEntry 19 }

tBgpInstancePlcyExportPolicy5    OBJECT-TYPE
    SYNTAX      TLPolicyNameOrExpOrEmpty
    MAX-ACCESS  read-create
    STATUS      current
    DESCRIPTION
        "The value of tBgpInstancePlcyExportPolicy5 specifies the fifth export
         policy."
    DEFVAL      { "" }
    ::= { tBgpInstancePlcyEntry 20 }

tBgpInstancePlcyExportPolicy6    OBJECT-TYPE
    SYNTAX      TLPolicyNameOrExpOrEmpty
    MAX-ACCESS  read-create
    STATUS      current
    DESCRIPTION
        "The value of tBgpInstancePlcyExportPolicy6 specifies the sixth export
         policy."
    DEFVAL      { "" }
    ::= { tBgpInstancePlcyEntry 21 }

tBgpInstancePlcyExportPolicy7    OBJECT-TYPE
    SYNTAX      TLPolicyNameOrExpOrEmpty
    MAX-ACCESS  read-create
    STATUS      current
    DESCRIPTION
        "The value of tBgpInstancePlcyExportPolicy7 specifies the seventh
         export policy."
    DEFVAL      { "" }
    ::= { tBgpInstancePlcyEntry 22 }

tBgpInstancePlcyExportPolicy8    OBJECT-TYPE
    SYNTAX      TLPolicyNameOrExpOrEmpty
    MAX-ACCESS  read-create
    STATUS      current
    DESCRIPTION
        "The value of tBgpInstancePlcyExportPolicy8 specifies the eighth export
         policy."
    DEFVAL      { "" }
    ::= { tBgpInstancePlcyEntry 23 }

tBgpInstancePlcyExportPolicy9    OBJECT-TYPE
    SYNTAX      TLPolicyNameOrExpOrEmpty
    MAX-ACCESS  read-create
    STATUS      current
    DESCRIPTION
        "The value of tBgpInstancePlcyExportPolicy9 specifies the ninth export
         policy."
    DEFVAL      { "" }
    ::= { tBgpInstancePlcyEntry 24 }

tBgpInstancePlcyExportPolicy10   OBJECT-TYPE
    SYNTAX      TLPolicyNameOrExpOrEmpty
    MAX-ACCESS  read-create
    STATUS      current
    DESCRIPTION
        "The value of tBgpInstancePlcyExportPolicy10 specifies the tenth export
         policy."
    DEFVAL      { "" }
    ::= { tBgpInstancePlcyEntry 25 }

tBgpInstancePlcyExportPolicy11   OBJECT-TYPE
    SYNTAX      TLPolicyNameOrExpOrEmpty
    MAX-ACCESS  read-create
    STATUS      current
    DESCRIPTION
        "The value of tBgpInstancePlcyExportPolicy11 specifies the eleventh
         export policy."
    DEFVAL      { "" }
    ::= { tBgpInstancePlcyEntry 26 }

tBgpInstancePlcyExportPolicy12   OBJECT-TYPE
    SYNTAX      TLPolicyNameOrExpOrEmpty
    MAX-ACCESS  read-create
    STATUS      current
    DESCRIPTION
        "The value of tBgpInstancePlcyExportPolicy12 specifies the twelfth
         export policy."
    DEFVAL      { "" }
    ::= { tBgpInstancePlcyEntry 27 }

tBgpInstancePlcyExportPolicy13   OBJECT-TYPE
    SYNTAX      TLPolicyNameOrExpOrEmpty
    MAX-ACCESS  read-create
    STATUS      current
    DESCRIPTION
        "The value of tBgpInstancePlcyExportPolicy13 specifies the thirteenth
         export policy."
    DEFVAL      { "" }
    ::= { tBgpInstancePlcyEntry 28 }

tBgpInstancePlcyExportPolicy14   OBJECT-TYPE
    SYNTAX      TLPolicyNameOrExpOrEmpty
    MAX-ACCESS  read-create
    STATUS      current
    DESCRIPTION
        "The value of tBgpInstancePlcyExportPolicy14 specifies the fourteenth
         export policy."
    DEFVAL      { "" }
    ::= { tBgpInstancePlcyEntry 29 }

tBgpInstancePlcyExportPolicy15   OBJECT-TYPE
    SYNTAX      TLPolicyNameOrExpOrEmpty
    MAX-ACCESS  read-create
    STATUS      current
    DESCRIPTION
        "The value of tBgpInstancePlcyExportPolicy15 specifies the fifteenth
         export policy."
    DEFVAL      { "" }
    ::= { tBgpInstancePlcyEntry 30 }

tBgpRibLeakImportPolicyTblLstCh  OBJECT-TYPE
    SYNTAX      TimeStamp
    MAX-ACCESS  read-only
    STATUS      current
    DESCRIPTION
        "The value of tBgpRibLeakImportPolicyTblLstCh indicates the last
         timestamp when an entry in the tBgpRibLeakImportPolicyTable was last
         changed."
    ::= { tBgpInstanceObjects 8 }

tBgpRibLeakImportPolicyTable     OBJECT-TYPE
    SYNTAX      SEQUENCE OF TBgpRibLeakImportPolicyEntry
    MAX-ACCESS  not-accessible
    STATUS      current
    DESCRIPTION
        "The tBgpRibLeakImportPolicyTable is the list of configured policies
         that are evaluated against all the leak-candidate RIB-INs of other
         routing instances. A matched leak-candidate RIB-IN that is accepted by
         one of the policies is leaked/copied into the local RIB-IN."
    ::= { tBgpInstanceObjects 9 }

tBgpRibLeakImportPolicyEntry     OBJECT-TYPE
    SYNTAX      TBgpRibLeakImportPolicyEntry
    MAX-ACCESS  not-accessible
    STATUS      current
    DESCRIPTION
        "An entry (conceptual row) in the tBgpRibLeakImportPolicyTable.

         An entry is created when an entry in tBgpInstanceEntry is. When
         created, all objects are initialized to their default values."
    INDEX       {
        tBgpInstanceIndex,
        tBgpRibLeakImportPolicyFamily
    }
    ::= { tBgpRibLeakImportPolicyTable 1 }

TBgpRibLeakImportPolicyEntry     ::= SEQUENCE
{
    tBgpRibLeakImportPolicyFamily    TmnxIpFamilyIdentifier,
    tBgpRibLeakImportPolicyLstCh     TimeStamp,
    tBgpRibLeakImportPolicy1         TXLPolicyNameOrExpOrEmpty,
    tBgpRibLeakImportPolicy2         TLPolicyNameOrExpOrEmpty,
    tBgpRibLeakImportPolicy3         TLPolicyNameOrExpOrEmpty,
    tBgpRibLeakImportPolicy4         TLPolicyNameOrExpOrEmpty,
    tBgpRibLeakImportPolicy5         TLPolicyNameOrExpOrEmpty,
    tBgpRibLeakImportPolicy6         TLPolicyNameOrExpOrEmpty,
    tBgpRibLeakImportPolicy7         TLPolicyNameOrExpOrEmpty,
    tBgpRibLeakImportPolicy8         TLPolicyNameOrExpOrEmpty,
    tBgpRibLeakImportPolicy9         TLPolicyNameOrExpOrEmpty,
    tBgpRibLeakImportPolicy10        TLPolicyNameOrExpOrEmpty,
    tBgpRibLeakImportPolicy11        TLPolicyNameOrExpOrEmpty,
    tBgpRibLeakImportPolicy12        TLPolicyNameOrExpOrEmpty,
    tBgpRibLeakImportPolicy13        TLPolicyNameOrExpOrEmpty,
    tBgpRibLeakImportPolicy14        TLPolicyNameOrExpOrEmpty,
    tBgpRibLeakImportPolicy15        TLPolicyNameOrExpOrEmpty
}

tBgpRibLeakImportPolicyFamily    OBJECT-TYPE
    SYNTAX      TmnxIpFamilyIdentifier
    MAX-ACCESS  not-accessible
    STATUS      current
    DESCRIPTION
        "The value of tBgpRibLeakImportPolicyFamily specifies the address
         family for which leak import policies apply."
    ::= { tBgpRibLeakImportPolicyEntry 1 }

tBgpRibLeakImportPolicyLstCh     OBJECT-TYPE
    SYNTAX      TimeStamp
    MAX-ACCESS  read-only
    STATUS      current
    DESCRIPTION
        "The value tBgpRibLeakImportPolicyLstCh indicates when an entry in
         tBgpRibLeakImportPolicyTable was last changed."
    ::= { tBgpRibLeakImportPolicyEntry 2 }

tBgpRibLeakImportPolicy1         OBJECT-TYPE
    SYNTAX      TXLPolicyNameOrExpOrEmpty
    MAX-ACCESS  read-create
    STATUS      current
    DESCRIPTION
        "The value of tBgpRibLeakImportPolicy1 specifies the first leak import
         policy."
    DEFVAL      { "" }
    ::= { tBgpRibLeakImportPolicyEntry 3 }

tBgpRibLeakImportPolicy2         OBJECT-TYPE
    SYNTAX      TLPolicyNameOrExpOrEmpty
    MAX-ACCESS  read-create
    STATUS      current
    DESCRIPTION
        "The value of tBgpRibLeakImportPolicy2 specifies the second leak import
         policy."
    DEFVAL      { "" }
    ::= { tBgpRibLeakImportPolicyEntry 4 }

tBgpRibLeakImportPolicy3         OBJECT-TYPE
    SYNTAX      TLPolicyNameOrExpOrEmpty
    MAX-ACCESS  read-create
    STATUS      current
    DESCRIPTION
        "The value of tBgpRibLeakImportPolicy3 specifies the third leak import
         policy."
    DEFVAL      { "" }
    ::= { tBgpRibLeakImportPolicyEntry 5 }

tBgpRibLeakImportPolicy4         OBJECT-TYPE
    SYNTAX      TLPolicyNameOrExpOrEmpty
    MAX-ACCESS  read-create
    STATUS      current
    DESCRIPTION
        "The value of tBgpRibLeakImportPolicy4 specifies the fourth leak import
         policy."
    DEFVAL      { "" }
    ::= { tBgpRibLeakImportPolicyEntry 6 }

tBgpRibLeakImportPolicy5         OBJECT-TYPE
    SYNTAX      TLPolicyNameOrExpOrEmpty
    MAX-ACCESS  read-create
    STATUS      current
    DESCRIPTION
        "The value of tBgpRibLeakImportPolicy5 specifies the fifth leak import
         policy."
    DEFVAL      { "" }
    ::= { tBgpRibLeakImportPolicyEntry 7 }

tBgpRibLeakImportPolicy6         OBJECT-TYPE
    SYNTAX      TLPolicyNameOrExpOrEmpty
    MAX-ACCESS  read-create
    STATUS      current
    DESCRIPTION
        "The value of tBgpRibLeakImportPolicy6 specifies the sixth leak import
         policy."
    DEFVAL      { "" }
    ::= { tBgpRibLeakImportPolicyEntry 8 }

tBgpRibLeakImportPolicy7         OBJECT-TYPE
    SYNTAX      TLPolicyNameOrExpOrEmpty
    MAX-ACCESS  read-create
    STATUS      current
    DESCRIPTION
        "The value of tBgpRibLeakImportPolicy7 specifies the seventh leak
         import policy."
    DEFVAL      { "" }
    ::= { tBgpRibLeakImportPolicyEntry 9 }

tBgpRibLeakImportPolicy8         OBJECT-TYPE
    SYNTAX      TLPolicyNameOrExpOrEmpty
    MAX-ACCESS  read-create
    STATUS      current
    DESCRIPTION
        "The value of tBgpRibLeakImportPolicy8 specifies the eighth leak import
         policy."
    DEFVAL      { "" }
    ::= { tBgpRibLeakImportPolicyEntry 10 }

tBgpRibLeakImportPolicy9         OBJECT-TYPE
    SYNTAX      TLPolicyNameOrExpOrEmpty
    MAX-ACCESS  read-create
    STATUS      current
    DESCRIPTION
        "The value of tBgpRibLeakImportPolicy9 specifies the ninth leak import
         policy."
    DEFVAL      { "" }
    ::= { tBgpRibLeakImportPolicyEntry 11 }

tBgpRibLeakImportPolicy10        OBJECT-TYPE
    SYNTAX      TLPolicyNameOrExpOrEmpty
    MAX-ACCESS  read-create
    STATUS      current
    DESCRIPTION
        "The value of tBgpRibLeakImportPolicy10 specifies the tenth leak import
         policy."
    DEFVAL      { "" }
    ::= { tBgpRibLeakImportPolicyEntry 12 }

tBgpRibLeakImportPolicy11        OBJECT-TYPE
    SYNTAX      TLPolicyNameOrExpOrEmpty
    MAX-ACCESS  read-create
    STATUS      current
    DESCRIPTION
        "The value of tBgpRibLeakImportPolicy11 specifies the eleventh leak
         import policy."
    DEFVAL      { "" }
    ::= { tBgpRibLeakImportPolicyEntry 13 }

tBgpRibLeakImportPolicy12        OBJECT-TYPE
    SYNTAX      TLPolicyNameOrExpOrEmpty
    MAX-ACCESS  read-create
    STATUS      current
    DESCRIPTION
        "The value of tBgpRibLeakImportPolicy12 specifies the twelfth leak
         import policy."
    DEFVAL      { "" }
    ::= { tBgpRibLeakImportPolicyEntry 14 }

tBgpRibLeakImportPolicy13        OBJECT-TYPE
    SYNTAX      TLPolicyNameOrExpOrEmpty
    MAX-ACCESS  read-create
    STATUS      current
    DESCRIPTION
        "The value of tBgpRibLeakImportPolicy13 specifies the thirteenth leak
         import policy."
    DEFVAL      { "" }
    ::= { tBgpRibLeakImportPolicyEntry 15 }

tBgpRibLeakImportPolicy14        OBJECT-TYPE
    SYNTAX      TLPolicyNameOrExpOrEmpty
    MAX-ACCESS  read-create
    STATUS      current
    DESCRIPTION
        "The value of tBgpRibLeakImportPolicy14 specifies the fourteenth leak
         import policy."
    DEFVAL      { "" }
    ::= { tBgpRibLeakImportPolicyEntry 16 }

tBgpRibLeakImportPolicy15        OBJECT-TYPE
    SYNTAX      TLPolicyNameOrExpOrEmpty
    MAX-ACCESS  read-create
    STATUS      current
    DESCRIPTION
        "The value of tBgpRibLeakImportPolicy15 specifies the fifteenth leak
         import policy."
    DEFVAL      { "" }
    ::= { tBgpRibLeakImportPolicyEntry 17 }

tBgpShortcutTunnelTblLstCh       OBJECT-TYPE
    SYNTAX      TimeStamp
    MAX-ACCESS  read-only
    STATUS      current
    DESCRIPTION
        "The value of tBgpShortcutTunnelTblLstCh indicates the last timestamp
         when an entry in the tBgpShortcutTunnelTable was last changed."
    ::= { tBgpInstanceObjects 10 }

tBgpShortcutTunnelTable          OBJECT-TYPE
    SYNTAX      SEQUENCE OF TBgpShortcutTunnelEntry
    MAX-ACCESS  not-accessible
    STATUS      current
    DESCRIPTION
        "The tBgpShortcutTunnelTable is the list of configured shortcut tunnel
         mechanisms for different family types for BGP unlabeled routes.

         The table entries are indexed by BGP instance and family type. Each
         entry denotes the tunnel selection used to resolve unlabeled BGP
         routes of a specific family type."
    ::= { tBgpInstanceObjects 11 }

tBgpShortcutTunnelEntry          OBJECT-TYPE
    SYNTAX      TBgpShortcutTunnelEntry
    MAX-ACCESS  not-accessible
    STATUS      current
    DESCRIPTION
        "An entry (conceptual row) in the tBgpShortcutTunnelTable.

         An entry is created when an entry in tBgpInstanceEntry is. When
         created, all objects are initialized to their default values."
    INDEX       {
        tBgpInstanceIndex,
        tBgpShortcutTunnelFamily
    }
    ::= { tBgpShortcutTunnelTable 1 }

TBgpShortcutTunnelEntry          ::= SEQUENCE
{
    tBgpShortcutTunnelFamily         TmnxIpFamilyIdentifier,
    tBgpShortcutTunnelLstCh          TimeStamp,
    tBgpShortcutTunnelResolution     TResolveStatus,
    tBgpShortcutTunnelLdp            TruthValue,
    tBgpShortcutTunnelRsvpTe         TruthValue,
    tBgpShortcutTunnelBgp            TruthValue,
    tBgpShortcutTunnelDisallowIgp    TruthValue,
    tBgpShortcutTunnelSrIsis         TruthValue,
    tBgpShortcutTunnelSrOspf         TruthValue,
    tBgpShortcutTunnelSrTe           TruthValue,
    tBgpShortcutTunnelAdminTags      TruthValue,
    tBgpShortcutTunnelSrPolicy       TruthValue,
    tBgpShortcutTunnelRibApi         TruthValue,
    tBgpShortcutTunnelMplsFwdPlcy    TruthValue,
    tBgpShortcutTunnelSrOspf3        TruthValue,
    tBgpShortcutTunnelFlexAlgoFb     TruthValue,
    tBgpShortcutTunnelEnforceUntagRt TBgpUntaggedRouteType
}

tBgpShortcutTunnelFamily         OBJECT-TYPE
    SYNTAX      TmnxIpFamilyIdentifier
    MAX-ACCESS  not-accessible
    STATUS      current
    DESCRIPTION
        "The value of tBgpShortcutTunnelFamily specifies the address family for
         which the shortcut tunnel selection applies."
    ::= { tBgpShortcutTunnelEntry 1 }

tBgpShortcutTunnelLstCh          OBJECT-TYPE
    SYNTAX      TimeStamp
    MAX-ACCESS  read-only
    STATUS      current
    DESCRIPTION
        "The value tBgpShortcutTunnelLstCh indicates when an entry in
         tBgpShortcutTunnelTable was last changed."
    ::= { tBgpShortcutTunnelEntry 2 }

tBgpShortcutTunnelResolution     OBJECT-TYPE
    SYNTAX      TResolveStatus
    MAX-ACCESS  read-create
    STATUS      current
    DESCRIPTION
        "The value of tBgpShortcutTunnelResolution specifies the resolution
         status used for resolving BGP next-hops belonging to a specific family
         type.

         When the value is 'filter', only selected tunnel types are used to
         resolve BGP  next-hops following TTM preference.

         When the value is 'any', any of the supported tunnel types are
         selected to resolve next-hops following TTM preference.

         When the value is 'disabled' none of the tunnel types are selected."
    DEFVAL      { disabled }
    ::= { tBgpShortcutTunnelEntry 3 }

tBgpShortcutTunnelLdp            OBJECT-TYPE
    SYNTAX      TruthValue
    MAX-ACCESS  read-create
    STATUS      current
    DESCRIPTION
        "The value of tBgpShortcutTunnelLdp specifies whether LDP tunnelling is
         used for IGP shortcuts to resolve paths to BGP next-hops belonging to
         a specific family."
    DEFVAL      { false }
    ::= { tBgpShortcutTunnelEntry 4 }

tBgpShortcutTunnelRsvpTe         OBJECT-TYPE
    SYNTAX      TruthValue
    MAX-ACCESS  read-create
    STATUS      current
    DESCRIPTION
        "The value of tBgpShortcutTunnelRsvpTe specifies whether RSVP
         tunnelling is used for IGP shortcuts to resolve paths to BGP next-hops
         belonging to a specific family."
    DEFVAL      { false }
    ::= { tBgpShortcutTunnelEntry 5 }

tBgpShortcutTunnelBgp            OBJECT-TYPE
    SYNTAX      TruthValue
    MAX-ACCESS  read-create
    STATUS      current
    DESCRIPTION
        "The value of tBgpShortcutTunnelBgp specifies whether BGP tunnelling is
         used for IGP shortcuts to resolve paths to BGP next-hops belonging to
         a specific family."
    DEFVAL      { false }
    ::= { tBgpShortcutTunnelEntry 6 }

tBgpShortcutTunnelDisallowIgp    OBJECT-TYPE
    SYNTAX      TruthValue
    MAX-ACCESS  read-create
    STATUS      current
    DESCRIPTION
        "The value of tBgpShortcutTunnelDisallowIgp specifies if IGP next-hop
         to the BGP next-hop is used as the next-hop as the last resort.

         A value of 'true', disallows the IGP next-hop to the BGP next-hop from
         being used as the next-hop as a last resort. This is used to prevent
         routing loops.

         A value of 'false' reverts the IGP shortcut next-hop evaluation
         process to the default of allowing IGP next-hops as the next-hop in
         the last resort.

         An 'inconsistentValue' error is returned if an attempt is made to set
         this object to a non-default value when none of the tunnelling
         mechanisms are selected"
    DEFVAL      { false }
    ::= { tBgpShortcutTunnelEntry 7 }

tBgpShortcutTunnelSrIsis         OBJECT-TYPE
    SYNTAX      TruthValue
    MAX-ACCESS  read-create
    STATUS      current
    DESCRIPTION
        "The value of tBgpShortcutTunnelSrIsis specifies whether SR ISIS is
         used for IGP shortcuts to resolve paths to BGP next-hops belonging to
         a specific family."
    DEFVAL      { false }
    ::= { tBgpShortcutTunnelEntry 8 }

tBgpShortcutTunnelSrOspf         OBJECT-TYPE
    SYNTAX      TruthValue
    MAX-ACCESS  read-create
    STATUS      current
    DESCRIPTION
        "The value of tBgpShortcutTunnelSrOspf specifies whether SR OSPF is
         used for IGP shortcuts to resolve paths to BGP next-hops belonging to
         a specific family."
    DEFVAL      { false }
    ::= { tBgpShortcutTunnelEntry 9 }

tBgpShortcutTunnelSrTe           OBJECT-TYPE
    SYNTAX      TruthValue
    MAX-ACCESS  read-create
    STATUS      current
    DESCRIPTION
        "The value of tBgpShortcutTunnelSrTe specifies whether SR Traffic
         Engineering is used for IGP shortcuts to resolve paths to BGP
         next-hops belonging to a specific family."
    DEFVAL      { false }
    ::= { tBgpShortcutTunnelEntry 10 }

tBgpShortcutTunnelAdminTags      OBJECT-TYPE
    SYNTAX      TruthValue
    MAX-ACCESS  read-create
    STATUS      current
    DESCRIPTION
        "The value of tBgpShortcutTunnelAdminTags specifies the system to  only
         consider LSPs marked with an admin-tag for next hop resolution.
         Untagged LSPs will not be considered.  When disabled this reverts to
         default behaviour. While tagged  SR-TE LSPs will be considered first,
         the system can fall back to using untagged LSP of other types and not
         exclude them."
    DEFVAL      { false }
    ::= { tBgpShortcutTunnelEntry 11 }

tBgpShortcutTunnelSrPolicy       OBJECT-TYPE
    SYNTAX      TruthValue
    MAX-ACCESS  read-create
    STATUS      current
    DESCRIPTION
        "The value of tBgpShortcutTunnelSrPolicy specifies whether SR Policy is
         used for IGP shortcuts to resolve paths to BGP next-hops belonging to
         a specific family."
    DEFVAL      { false }
    ::= { tBgpShortcutTunnelEntry 12 }

tBgpShortcutTunnelRibApi         OBJECT-TYPE
    SYNTAX      TruthValue
    MAX-ACCESS  read-create
    STATUS      current
    DESCRIPTION
        "The value of tBgpShortcutTunnelRibApi specifies whether RIB API is
         used for IGP shortcuts to resolve paths to BGP next-hops belonging to
         a specific family."
    DEFVAL      { false }
    ::= { tBgpShortcutTunnelEntry 13 }

tBgpShortcutTunnelMplsFwdPlcy    OBJECT-TYPE
    SYNTAX      TruthValue
    MAX-ACCESS  read-create
    STATUS      current
    DESCRIPTION
        "The value of tBgpShortcutTunnelMplsFwdPlcy specifies whether MPLS
         Forwarding policy is used for IGP shortcuts to resolve  paths to BGP
         next-hops belonging to a specific family."
    DEFVAL      { false }
    ::= { tBgpShortcutTunnelEntry 14 }

tBgpShortcutTunnelSrOspf3        OBJECT-TYPE
    SYNTAX      TruthValue
    MAX-ACCESS  read-create
    STATUS      current
    DESCRIPTION
        "The value of tBgpShortcutTunnelSrOspf3 specifies whether SR OSPF3 is
         used for IGP shortcuts to resolve paths to BGP next-hops belonging to
         a specific family."
    DEFVAL      { false }
    ::= { tBgpShortcutTunnelEntry 15 }

tBgpShortcutTunnelFlexAlgoFb     OBJECT-TYPE
    SYNTAX      TruthValue
    MAX-ACCESS  read-create
    STATUS      current
    DESCRIPTION
        "Allow the use of routes with another flex-algo-id than configured as a
         fallback option"
    DEFVAL      { false }
    ::= { tBgpShortcutTunnelEntry 16 }

tBgpShortcutTunnelEnforceUntagRt OBJECT-TYPE
    SYNTAX      TBgpUntaggedRouteType
    MAX-ACCESS  read-create
    STATUS      current
    DESCRIPTION
        "The value of tBgpShortcutTunnelEnforceUntagRt specifies if
         untagged-routes should not fall back to tagged tunnels for next-hop
         resolution."
    DEFVAL      { none }
    ::= { tBgpShortcutTunnelEntry 17 }

tBgpLabelRtTunnelTblLstCh        OBJECT-TYPE
    SYNTAX      TimeStamp
    MAX-ACCESS  read-only
    STATUS      current
    DESCRIPTION
        "The value of tBgpLabelRtTunnelTblLstCh indicates the last timestamp
         when an entry in the tBgpLabelRtTunnelTable was last changed."
    ::= { tBgpInstanceObjects 12 }

tBgpLabelRtTunnelTable           OBJECT-TYPE
    SYNTAX      SEQUENCE OF TBgpLabelRtTunnelEntry
    MAX-ACCESS  not-accessible
    STATUS      current
    DESCRIPTION
        "The tBgpLabelRtTunnelTable is the list of configured tunnel mechanisms
         for different family types while resolving BGP labelled routes.

         The table entries are indexed by BGP instance and family type. Each
         entry denotes the tunnel selection used to resolve labelled BGP routes
         of a specific family type."
    ::= { tBgpInstanceObjects 13 }

tBgpLabelRtTunnelEntry           OBJECT-TYPE
    SYNTAX      TBgpLabelRtTunnelEntry
    MAX-ACCESS  not-accessible
    STATUS      current
    DESCRIPTION
        "An entry (conceptual row) in the tBgpLabelRtTunnelTable.

         An entry is created when an entry in tBgpInstanceEntry is. When
         created, all objects are initialized to their default values."
    INDEX       {
        tBgpInstanceIndex,
        tBgpLabelRtTunnelFamily
    }
    ::= { tBgpLabelRtTunnelTable 1 }

TBgpLabelRtTunnelEntry           ::= SEQUENCE
{
    tBgpLabelRtTunnelFamily          TmnxIpFamilyIdentifier,
    tBgpLabelRtTunnelLstCh           TimeStamp,
    tBgpLabelRtTunnelResolution      TResolveStatus,
    tBgpLabelRtTunnelLdp             TruthValue,
    tBgpLabelRtTunnelRsvpTe          TruthValue,
    tBgpLabelRtTunnelSrIsis          TruthValue,
    tBgpLabelRtTunnelSrOspf          TruthValue,
    tBgpLabelRtTunnelBgp             TruthValue,
    tBgpLabelRtTunnelSrTe            TruthValue,
    tBgpLabelRtTunnelUdp             TruthValue,
    tBgpLabelRtTunnelAdminTags       TruthValue,
    tBgpLabelRtTunnelSrPolicy        TruthValue,
    tBgpLabelRtTunnelRibApi          TruthValue,
    tBgpLabelRtTunnelMplsFwdPlcy     TruthValue,
    tBgpLabelRtTunnelSrOspf3         TruthValue,
    tBgpLabelRtTunnelFlexAlgoFb      TruthValue,
    tBgpLabelRtTunnelEnforceUntagRt  TBgpUntaggedRouteType,
    tBgpLabelRtTunnelMaxEcmpRoutes   Unsigned32
}

tBgpLabelRtTunnelFamily          OBJECT-TYPE
    SYNTAX      TmnxIpFamilyIdentifier
    MAX-ACCESS  not-accessible
    STATUS      current
    DESCRIPTION
        "The value of tBgpLabelRtTunnelFamily specifies the address family for
         which the tunnel selection applies."
    ::= { tBgpLabelRtTunnelEntry 1 }

tBgpLabelRtTunnelLstCh           OBJECT-TYPE
    SYNTAX      TimeStamp
    MAX-ACCESS  read-only
    STATUS      current
    DESCRIPTION
        "The value tBgpLabelRtTunnelLstCh indicates when an entry in
         tBgpLabelRtTunnelTable was last changed."
    ::= { tBgpLabelRtTunnelEntry 2 }

tBgpLabelRtTunnelResolution      OBJECT-TYPE
    SYNTAX      TResolveStatus
    MAX-ACCESS  read-create
    STATUS      current
    DESCRIPTION
        "The value of tBgpLabelRtTunnelResolution specifies the resolution
         status used for resolving BGP labeled routes belonging to a specific
         family type.

         When the value is 'filter', only selected tunnel types are used to
         resolve BGP labeled routes following TTM preference.

         When the value is 'any', any of the supported tunnel types are
         selected to resolve routes following TTM preference.

         When the value is 'disabled' none of the tunnel types are selected."
    DEFVAL      { filter }
    ::= { tBgpLabelRtTunnelEntry 3 }

tBgpLabelRtTunnelLdp             OBJECT-TYPE
    SYNTAX      TruthValue
    MAX-ACCESS  read-create
    STATUS      current
    DESCRIPTION
        "The value of tBgpLabelRtTunnelLdp specifies whether LDP LSPs are
         allowed to be used for resolving BGP labeled routes belonging to a
         specific family type."
    DEFVAL      { true }
    ::= { tBgpLabelRtTunnelEntry 4 }

tBgpLabelRtTunnelRsvpTe          OBJECT-TYPE
    SYNTAX      TruthValue
    MAX-ACCESS  read-create
    STATUS      current
    DESCRIPTION
        "The value of tBgpLabelRtTunnelRsvpTe specifies whether RSVP-TE LSPs
         are allowed to be used for resolving BGP labeled routes belonging to a
         specific family type."
    DEFVAL      { false }
    ::= { tBgpLabelRtTunnelEntry 5 }

tBgpLabelRtTunnelSrIsis          OBJECT-TYPE
    SYNTAX      TruthValue
    MAX-ACCESS  read-create
    STATUS      current
    DESCRIPTION
        "The value of tBgpLabelRtTunnelSrIsis specifies whether SR ISIS is
         allowed to be used for resolving BGP labeled routes belonging to a
         specific family type."
    DEFVAL      { false }
    ::= { tBgpLabelRtTunnelEntry 6 }

tBgpLabelRtTunnelSrOspf          OBJECT-TYPE
    SYNTAX      TruthValue
    MAX-ACCESS  read-create
    STATUS      current
    DESCRIPTION
        "The value of tBgpLabelRtTunnelSrOspf specifies whether SR OSPF is
         allowed to be used for resolving BGP labeled routes belonging to a
         specific family type."
    DEFVAL      { false }
    ::= { tBgpLabelRtTunnelEntry 7 }

tBgpLabelRtTunnelBgp             OBJECT-TYPE
    SYNTAX      TruthValue
    MAX-ACCESS  read-create
    STATUS      current
    DESCRIPTION
        "The value of tBgpLabelRtTunnelBgp specifies whether BGP is allowed to
         be used for resolving BGP labeled routes belonging to a specific
         family type.

         For family type vpn, the default value is true. For other families it
         is false."
    DEFVAL      { false }
    ::= { tBgpLabelRtTunnelEntry 8 }

tBgpLabelRtTunnelSrTe            OBJECT-TYPE
    SYNTAX      TruthValue
    MAX-ACCESS  read-create
    STATUS      current
    DESCRIPTION
        "The value of tBgpLabelRtTunnelSrTe specifies whether SR Traffic
         Engineering is allowed to be used for resolving BGP labeled routes
         belonging to a specific family type."
    DEFVAL      { false }
    ::= { tBgpLabelRtTunnelEntry 9 }

tBgpLabelRtTunnelUdp             OBJECT-TYPE
    SYNTAX      TruthValue
    MAX-ACCESS  read-create
    STATUS      current
    DESCRIPTION
        "The value of tBgpLabelRtTunnelUdp specifies whether UDP is allowed to
         be used for resolving BGP labeled routes belonging to a specific
         family type."
    DEFVAL      { false }
    ::= { tBgpLabelRtTunnelEntry 10 }

tBgpLabelRtTunnelAdminTags       OBJECT-TYPE
    SYNTAX      TruthValue
    MAX-ACCESS  read-create
    STATUS      current
    DESCRIPTION
        "The value of tBgpLabelRtTunnelAdminTags specifies the system to only
         consider LSPs marked with an admin-tag for next hop resolution.
         Untagged LSPs will not be considered.  When disabled this reverts to
         default behaviour. While tagged RSVP  and SR-TE LSPs will be
         considered first, the system can fall back to using untagged LSP of
         other types and not exclude them."
    DEFVAL      { false }
    ::= { tBgpLabelRtTunnelEntry 11 }

tBgpLabelRtTunnelSrPolicy        OBJECT-TYPE
    SYNTAX      TruthValue
    MAX-ACCESS  read-create
    STATUS      current
    DESCRIPTION
        "The value of tBgpLabelRtTunnelSrPolicy specifies whether Sr-policy is
         allowed to be used for resolving BGP labeled routes belonging to a
         specific family type."
    DEFVAL      { false }
    ::= { tBgpLabelRtTunnelEntry 12 }

tBgpLabelRtTunnelRibApi          OBJECT-TYPE
    SYNTAX      TruthValue
    MAX-ACCESS  read-create
    STATUS      current
    DESCRIPTION
        "The value of tBgpLabelRtTunnelRibApi specifies whether RIB API is
         allowed to be used for resolving BGP labeled routes belonging to a
         specific family type."
    DEFVAL      { false }
    ::= { tBgpLabelRtTunnelEntry 13 }

tBgpLabelRtTunnelMplsFwdPlcy     OBJECT-TYPE
    SYNTAX      TruthValue
    MAX-ACCESS  read-create
    STATUS      current
    DESCRIPTION
        "The value of tBgpLabelRtTunnelMplsFwdPlcy specifies whether MPLS
         Forwarding Policy is allowed to be used for resolving BGP labeled
         routes belonging to  a specific family type."
    DEFVAL      { false }
    ::= { tBgpLabelRtTunnelEntry 14 }

tBgpLabelRtTunnelSrOspf3         OBJECT-TYPE
    SYNTAX      TruthValue
    MAX-ACCESS  read-create
    STATUS      current
    DESCRIPTION
        "The value of tBgpLabelRtTunnelSrOspf3 specifies whether SR OSPF3 is
         allowed to be used for resolving BGP labeled routes belonging to a
         specific family type."
    DEFVAL      { false }
    ::= { tBgpLabelRtTunnelEntry 15 }

tBgpLabelRtTunnelFlexAlgoFb      OBJECT-TYPE
    SYNTAX      TruthValue
    MAX-ACCESS  read-create
    STATUS      current
    DESCRIPTION
        "Allow the use of routes with another flex-algo-id than configured as a
         fallback option"
    DEFVAL      { false }
    ::= { tBgpLabelRtTunnelEntry 16 }

tBgpLabelRtTunnelEnforceUntagRt  OBJECT-TYPE
    SYNTAX      TBgpUntaggedRouteType
    MAX-ACCESS  read-create
    STATUS      current
    DESCRIPTION
        "The value of tBgpLabelRtTunnelEnforceUntagRt specifies if
         untagged-routes should not fall back to tagged tunnels for next-hop
         resolution."
    DEFVAL      { none }
    ::= { tBgpLabelRtTunnelEntry 17 }

tBgpLabelRtTunnelMaxEcmpRoutes   OBJECT-TYPE
    SYNTAX      Unsigned32 (1..32)
    MAX-ACCESS  read-create
    STATUS      current
    DESCRIPTION
        "The value of tBgpLabelRtTunnelMaxEcmpRoutes specifies the maximum
         number of equal cost paths that can be picked up from the tunnel
         table."
    DEFVAL      { 1 }
    ::= { tBgpLabelRtTunnelEntry 18 }

tBgpInstanceMultiPathTable       OBJECT-TYPE
    SYNTAX      SEQUENCE OF TBgpInstanceMultiPathEntry
    MAX-ACCESS  not-accessible
    STATUS      obsolete
    DESCRIPTION
        "tBgpInstanceMultiPathTable consists of information about BGP multipath
         on each running instance of BGP.

         This table is deprecated and replaced with tBgpInstMultipathNgTable."
    ::= { tBgpInstanceObjects 14 }

tBgpInstanceMultiPathEntry       OBJECT-TYPE
    SYNTAX      TBgpInstanceMultiPathEntry
    MAX-ACCESS  not-accessible
    STATUS      current
    DESCRIPTION
        "An entry (conceptual row) in the tBgpInstanceMultiPathTable. Each
         entry represents an instance of BGP running on the virtual router."
    AUGMENTS    { tBgpInstanceEntry }
    ::= { tBgpInstanceMultiPathTable 1 }

TBgpInstanceMultiPathEntry       ::= SEQUENCE
{
    tBgpInstanceMultipathBgp         Integer32,
    tBgpInstanceMultipathEBgp        Integer32,
    tBgpInstanceMultipathIBgp        Integer32,
    tBgpInstanceMultipathRestrict    INTEGER
}

tBgpInstanceMultipathBgp         OBJECT-TYPE
    SYNTAX      Integer32 (1..64)
    UNITS       "number-of-hops"
    MAX-ACCESS  read-create
    STATUS      current
    DESCRIPTION
        "The value of tBgpInstanceMultipathBgp specifies if BGP multipath is
         enabled or disabled for this instance.

         A value of '1' would disable BGP multipath.

         Any other value would specify the number of hops for BGP Multipath."
    DEFVAL      { 1 }
    ::= { tBgpInstanceMultiPathEntry 1 }

tBgpInstanceMultipathEBgp        OBJECT-TYPE
    SYNTAX      Integer32 (0..64)
    UNITS       "number-of-hops"
    MAX-ACCESS  read-create
    STATUS      current
    DESCRIPTION
        "The value of tBgpInstanceMultipathEBgp specifies the maximum number of
         paths that can be installed into RTM when the best path is EBGP and
         the EIBGP option is not present.

         A value of '0' would disable EBGP multipath.

         Any other value would specify the number of hops for EBGP Multipath."
    DEFVAL      { 0 }
    ::= { tBgpInstanceMultiPathEntry 2 }

tBgpInstanceMultipathIBgp        OBJECT-TYPE
    SYNTAX      Integer32 (0..64)
    UNITS       "number-of-hops"
    MAX-ACCESS  read-create
    STATUS      current
    DESCRIPTION
        "The value of tBgpInstanceMultipathIBgp specifies the maximum number of
         paths that can be installed into RTM when the best path is IBGP and
         the EIBGP option is not present.

         A value of '0' would disable IBGP multipath.

         Any other value would specify the number of hops for IBGP Multipath."
    DEFVAL      { 0 }
    ::= { tBgpInstanceMultiPathEntry 3 }

tBgpInstanceMultipathRestrict    OBJECT-TYPE
    SYNTAX      INTEGER {
        sameAsPathLength (1),
        sameNeighborAs   (2),
        exactAsPath      (3)
    }
    MAX-ACCESS  read-create
    STATUS      current
    DESCRIPTION
        "When the value of tBgpInstanceMultipathRestrict is set to
         'sameAsPathLength', it forces multipaths to have the same AS path
          length (unless as-path-ignore is configured).

         When the value of tBgpInstanceMultipathRestrict is set to
         'sameNeighborAs', it forces multipaths to have the same AS path length
         (unless as-path-ignore is configured) and the same neighbor AS.

         When the value of tBgpInstanceMultipathRestrict is set to
         'exactAsPath' it forces multipaths to have the exact same AS paths,
         meaning the same ASNs in exactly the same order and contained in the
         exactly the same types of elements."
    DEFVAL      { sameAsPathLength }
    ::= { tBgpInstanceMultiPathEntry 4 }

tBgpRibControlTblLstCh           OBJECT-TYPE
    SYNTAX      TimeStamp
    MAX-ACCESS  read-only
    STATUS      current
    DESCRIPTION
        "The value of tBgpRibControlTblLstCh indicates the last timestamp when
         an entry in the tBgpRibControlTable was last changed."
    ::= { tBgpInstanceObjects 15 }

tBgpRibControlTable              OBJECT-TYPE
    SYNTAX      SEQUENCE OF TBgpRibControlEntry
    MAX-ACCESS  not-accessible
    STATUS      current
    DESCRIPTION
        "The tBgpRibControlTable consists of information about the routes in
         the RTM which can be imported into its family RIB."
    ::= { tBgpInstanceObjects 16 }

tBgpRibControlEntry              OBJECT-TYPE
    SYNTAX      TBgpRibControlEntry
    MAX-ACCESS  not-accessible
    STATUS      current
    DESCRIPTION
        "An entry (conceptual row) in the tBgpRibControlTable.

         An entry is created when an entry in tBgpInstanceEntry is. When
         created, all objects are initialized to their default values."
    INDEX       {
        tBgpInstanceIndex,
        tBgpRibRouteImportFamily
    }
    ::= { tBgpRibControlTable 1 }

TBgpRibControlEntry              ::= SEQUENCE
{
    tBgpRibRouteImportFamily         TmnxIpFamilyIdentifier,
    tBgpRibControlLstCh              TimeStamp,
    tBgpRibImportFromRtmPolicy       TLPolicyStatementNameOrEmpty
}

tBgpRibRouteImportFamily         OBJECT-TYPE
    SYNTAX      TmnxIpFamilyIdentifier
    MAX-ACCESS  not-accessible
    STATUS      current
    DESCRIPTION
        "The value of tBgpRibRouteImportFamily specifies the address family RIB
         where routes can be imported from the RTM."
    ::= { tBgpRibControlEntry 1 }

tBgpRibControlLstCh              OBJECT-TYPE
    SYNTAX      TimeStamp
    MAX-ACCESS  read-only
    STATUS      current
    DESCRIPTION
        "The value tBgpRibControlLstCh indicates when an entry in
         tBgpRibControlTable was last changed."
    ::= { tBgpRibControlEntry 2 }

tBgpRibImportFromRtmPolicy       OBJECT-TYPE
    SYNTAX      TLPolicyStatementNameOrEmpty
    MAX-ACCESS  read-create
    STATUS      current
    DESCRIPTION
        "The value of tBgpRibImportFromRtmPolicy specifies the policy that
         should be executed before allowing a route from the RTM to be imported
         into this family's RIB."
    DEFVAL      { "" }
    ::= { tBgpRibControlEntry 3 }

tBgpOptRouteReflectionTblLstCh   OBJECT-TYPE
    SYNTAX      TimeStamp
    MAX-ACCESS  read-only
    STATUS      current
    DESCRIPTION
        "The value of tBgpOptRouteReflectionTblLstCh indicates the timestamp
         when an entry in the tBgpOptRouteReflectionTable was last changed."
    ::= { tBgpInstanceObjects 17 }

tBgpOptRouteReflectionTable      OBJECT-TYPE
    SYNTAX      SEQUENCE OF TBgpOptRouteReflectionEntry
    MAX-ACCESS  not-accessible
    STATUS      current
    DESCRIPTION
        "The tBgpOptRouteReflectionTable consists of information about the BGP
         optimal route reflection parameters.

         The table entries are indexed by BGP instance."
    ::= { tBgpInstanceObjects 18 }

tBgpOptRouteReflectionEntry      OBJECT-TYPE
    SYNTAX      TBgpOptRouteReflectionEntry
    MAX-ACCESS  not-accessible
    STATUS      current
    DESCRIPTION
        "An entry (conceptual row) in the tBgpOptRouteReflectionTable.

         An entry is created when an entry in tBgpInstanceEntry is. When
         created, all objects are initialized to their default values."
    INDEX       { tBgpInstanceIndex }
    ::= { tBgpOptRouteReflectionTable 1 }

TBgpOptRouteReflectionEntry      ::= SEQUENCE
{
    tBgpORRSpfMaxWaitTime            Unsigned32,
    tBgpORRSpfInitialWaitTime        Unsigned32,
    tBgpORRSpfSecondWaitTime         Unsigned32
}

tBgpORRSpfMaxWaitTime            OBJECT-TYPE
    SYNTAX      Unsigned32 (1..600)
    UNITS       "minutes"
    MAX-ACCESS  read-create
    STATUS      current
    DESCRIPTION
        "The value of tBgpORRSpfMaxWaitTime specifies the maximum hold-off time
         to start a new spf run after a spf trigger is detected."
    DEFVAL      { 60 }
    ::= { tBgpOptRouteReflectionEntry 1 }

tBgpORRSpfInitialWaitTime        OBJECT-TYPE
    SYNTAX      Unsigned32 (1..300)
    UNITS       "minutes"
    MAX-ACCESS  read-create
    STATUS      current
    DESCRIPTION
        "The value of tBgpORRSpfInitialWaitTime specifies the initial hold-off
         time after a period of stability before starting a new spf run to
         calculate the cost from an optimal-route-reflection location to a BGP
         next-hop."
    DEFVAL      { 5 }
    ::= { tBgpOptRouteReflectionEntry 2 }

tBgpORRSpfSecondWaitTime         OBJECT-TYPE
    SYNTAX      Unsigned32 (1..300)
    UNITS       "minutes"
    MAX-ACCESS  read-create
    STATUS      current
    DESCRIPTION
        "The value of tBgpORRSpfSecondWaitTime specifies the additional
         hold-off time before starting a new spf run if further spf triggers
         are received within the initial wait time."
    DEFVAL      { 15 }
    ::= { tBgpOptRouteReflectionEntry 3 }

tBgpORRLocationTblLstCh          OBJECT-TYPE
    SYNTAX      TimeStamp
    MAX-ACCESS  read-only
    STATUS      current
    DESCRIPTION
        "The value of tBgpORRLocationTblLstCh indicates the timestamp when an
         entry in the tBgpORRLocationTable was last changed."
    ::= { tBgpInstanceObjects 19 }

tBgpORRLocationTable             OBJECT-TYPE
    SYNTAX      SEQUENCE OF TBgpORRLocationEntry
    MAX-ACCESS  not-accessible
    STATUS      current
    DESCRIPTION
        "The tBgpORRLocationTable consists of information about the BGP optimal
         route reflection location parameters. The table entries are indexed by
         BGP instance and Location ID."
    ::= { tBgpInstanceObjects 20 }

tBgpORRLocationEntry             OBJECT-TYPE
    SYNTAX      TBgpORRLocationEntry
    MAX-ACCESS  not-accessible
    STATUS      current
    DESCRIPTION
        "An entry (conceptual row) in the tBgpORRLocationTable.

         An entry is created when an entry in tBgpInstanceEntry is. When
         created, all objects are initialized to their default values."
    INDEX       {
        tBgpInstanceIndex,
        tBgpORRLocationId
    }
    ::= { tBgpORRLocationTable 1 }

TBgpORRLocationEntry             ::= SEQUENCE
{
    tBgpORRLocationId                Unsigned32,
    tBgpORRLocationLstCh             TimeStamp,
    tBgpORRLocationRowStatus         RowStatus,
    tBgpORRPrimaryIPAddrType         InetAddressType,
    tBgpORRPrimaryIPAddr             InetAddress,
    tBgpORRSecondaryIPAddrType       InetAddressType,
    tBgpORRSecondaryIPAddr           InetAddress,
    tBgpORRTertiaryIPAddrType        InetAddressType,
    tBgpORRTertiaryIPAddr            InetAddress,
    tBgpORRPrimaryIPv6AddrType       InetAddressType,
    tBgpORRPrimaryIPv6Addr           InetAddress,
    tBgpORRSecondaryIPv6AddrType     InetAddressType,
    tBgpORRSecondaryIPv6Addr         InetAddress,
    tBgpORRTertiaryIPv6AddrType      InetAddressType,
    tBgpORRTertiaryIPv6Addr          InetAddress
}

tBgpORRLocationId                OBJECT-TYPE
    SYNTAX      Unsigned32 (1..255)
    MAX-ACCESS  not-accessible
    STATUS      current
    DESCRIPTION
        "The value of tBgpORRLocationId identifies an optimal-route-reflection
         location. A bgp neighbor can be associated with a location if it is a
         route-reflector client."
    ::= { tBgpORRLocationEntry 1 }

tBgpORRLocationLstCh             OBJECT-TYPE
    SYNTAX      TimeStamp
    MAX-ACCESS  read-only
    STATUS      current
    DESCRIPTION
        "The value tBgpORRLocationLstCh indicates when an entry in
         tBgpORRLocationTable was last changed."
    ::= { tBgpORRLocationEntry 2 }

tBgpORRLocationRowStatus         OBJECT-TYPE
    SYNTAX      RowStatus
    MAX-ACCESS  read-create
    STATUS      current
    DESCRIPTION
        "RowStatus for the ORR Location entry."
    ::= { tBgpORRLocationEntry 3 }

tBgpORRPrimaryIPAddrType         OBJECT-TYPE
    SYNTAX      InetAddressType
    MAX-ACCESS  read-create
    STATUS      current
    DESCRIPTION
        "The value of tBgpORRPrimaryIPAddrType specifies the address type of
         the primary IP address. tBgpORRPrimaryIPAddrType can be either unknown
         or ipv4."
    ::= { tBgpORRLocationEntry 4 }

tBgpORRPrimaryIPAddr             OBJECT-TYPE
    SYNTAX      InetAddress (SIZE (0|4|16))
    MAX-ACCESS  read-create
    STATUS      current
    DESCRIPTION
        "The value of tBgpORRPrimaryIPAddr specifies the preferred IPv4 address
         to calculate the optimal-route-reflection cost from the associated
         location to a bgp next-hop.

         If the tBgpORRPrimaryIPAddrType is set to ipv4, then the primary IP
         address is a IPv4 address.

         If the primary IP address is reset, tBgpORRPrimaryIPAddrType is set to
         unknown and tBgpORRPrimaryIPAddr returns a null string."
    ::= { tBgpORRLocationEntry 5 }

tBgpORRSecondaryIPAddrType       OBJECT-TYPE
    SYNTAX      InetAddressType
    MAX-ACCESS  read-create
    STATUS      current
    DESCRIPTION
        "The value of tBgpORRSecondaryIPAddrType specifies the address type of
         the secondary IP address. tBgpORRSecondaryIPAddrType can be either
         unknown or ipv4."
    ::= { tBgpORRLocationEntry 6 }

tBgpORRSecondaryIPAddr           OBJECT-TYPE
    SYNTAX      InetAddress (SIZE (0|4|16))
    MAX-ACCESS  read-create
    STATUS      current
    DESCRIPTION
        "The value of tBgpORRSecondaryIPAddr specifies the second preferred
         IPv4 address to calculate the optimal-route-reflection cost from the
         associated location to a bgp next-hop.

         If the tBgpORRSecondaryIPAddrType is set to ipv4, then the secondary
         IP address is a IPv4 address.

         If the secondary IP address is reset, tBgpORRSecondaryIPAddrType is
         set to unknown and tBgpORRSecondaryIPAddr returns a null string."
    ::= { tBgpORRLocationEntry 7 }

tBgpORRTertiaryIPAddrType        OBJECT-TYPE
    SYNTAX      InetAddressType
    MAX-ACCESS  read-create
    STATUS      current
    DESCRIPTION
        "The value of tBgpORRTertiaryIPAddrType specifies the address type of
         the tertiary IP address. tBgpORRTertiaryIPAddrType can be either
         unknown or ipv4."
    ::= { tBgpORRLocationEntry 8 }

tBgpORRTertiaryIPAddr            OBJECT-TYPE
    SYNTAX      InetAddress (SIZE (0|4|16))
    MAX-ACCESS  read-create
    STATUS      current
    DESCRIPTION
        "The value of tBgpORRTertiaryIPAddr specifies the third preferred IPv4
         address to calculate the optimal-route-reflection cost from the
         associated location to a bgp next-hop.

         If the tBgpORRTertiaryIPAddrType is set to ipv4, then the tertiary IP
         address is a IPv4 address.

         If the tertiary IP address is reset, tBgpORRTertiaryIPAddrType is set
         to unknown and tBgpORRTertiaryIPAddr returns a null string."
    ::= { tBgpORRLocationEntry 9 }

tBgpORRPrimaryIPv6AddrType       OBJECT-TYPE
    SYNTAX      InetAddressType
    MAX-ACCESS  read-create
    STATUS      current
    DESCRIPTION
        "The value of tBgpORRPrimaryIPv6AddrType specifies the address type of
         the primary IP address. tBgpORRPrimaryIPv6AddrType can be either
         unknown or ipv6."
    ::= { tBgpORRLocationEntry 10 }

tBgpORRPrimaryIPv6Addr           OBJECT-TYPE
    SYNTAX      InetAddress (SIZE (0|16))
    MAX-ACCESS  read-create
    STATUS      current
    DESCRIPTION
        "The value of tBgpORRPrimaryIPv6Addr specifies the preferred IPv6
         address to calculate the optimal-route-reflection cost from the
         associated location to a bgp next-hop.

         If the tBgpORRPrimaryIPAddrType is set to ipv6, then the primary IP
         address is a IPv6 address.

         If the primary IP address is reset, tBgpORRPrimaryIPv6AddrType is set
         to unknown and tBgpORRPrimaryIPv6Addr returns a null string."
    ::= { tBgpORRLocationEntry 11 }

tBgpORRSecondaryIPv6AddrType     OBJECT-TYPE
    SYNTAX      InetAddressType
    MAX-ACCESS  read-create
    STATUS      current
    DESCRIPTION
        "The value of tBgpORRSecondaryIPv6AddrType specifies the address type
         of the secondary IP address. tBgpORRSecondaryIPv6AddrType can be
         either unknown or ipv6."
    ::= { tBgpORRLocationEntry 12 }

tBgpORRSecondaryIPv6Addr         OBJECT-TYPE
    SYNTAX      InetAddress (SIZE (0|16))
    MAX-ACCESS  read-create
    STATUS      current
    DESCRIPTION
        "The value of tBgpORRSecondaryIPv6Addr specifies the second preferred
         IPv6 address to calculate the optimal-route-reflection cost from the
         associated location to a bgp next-hop.

         If the tBgpORRSecondaryIPv6AddrType is set to ipv6, then the secondary
         IP address is a IPv6 address.

         If the secondary IP address is reset, tBgpORRSecondaryIPv6AddrType is
         set to unknown and tBgpORRSecondaryIPv6Addr returns a null string."
    ::= { tBgpORRLocationEntry 13 }

tBgpORRTertiaryIPv6AddrType      OBJECT-TYPE
    SYNTAX      InetAddressType
    MAX-ACCESS  read-create
    STATUS      current
    DESCRIPTION
        "The value of tBgpORRTertiaryIPv6AddrType specifies the address type of
         the tertiary IP address. tBgpORRTertiaryIPAddrType can be either
         unknown or ipv6."
    ::= { tBgpORRLocationEntry 14 }

tBgpORRTertiaryIPv6Addr          OBJECT-TYPE
    SYNTAX      InetAddress (SIZE (0|16))
    MAX-ACCESS  read-create
    STATUS      current
    DESCRIPTION
        "The value of tBgpORRTertiaryIPv6Addr specifies the third preferred
         IPv6 address to calculate the optimal-route-reflection cost from the
         associated location to a bgp next-hop.

         If the tBgpORRTertiaryIPAddrType is set to ipv6, then the tertiary IP
         address is a IPv6 address.

         If the tertiary IP address is reset, tBgpORRTertiaryIPv6AddrType is
         set to unknown and tBgpORRTertiaryIPAddr returns a null string."
    ::= { tBgpORRLocationEntry 15 }

tBgpInstanceAddPathTblLstCh      OBJECT-TYPE
    SYNTAX      TimeStamp
    MAX-ACCESS  read-only
    STATUS      current
    DESCRIPTION
        "The value of tBgpInstanceAddPathTblLstCh indicates the timestamp when
         an entry in the tBgpInstanceAddPathTable was last changed."
    ::= { tBgpInstanceObjects 21 }

tBgpInstanceAddPathTable         OBJECT-TYPE
    SYNTAX      SEQUENCE OF TBgpInstanceAddPathEntry
    MAX-ACCESS  not-accessible
    STATUS      current
    DESCRIPTION
        "The tBgpInstanceAddPathTable consists of information about the BGP Add
         Path parameters.

         The table entries are indexed by BGP instance."
    ::= { tBgpInstanceObjects 22 }

tBgpInstanceAddPathEntry         OBJECT-TYPE
    SYNTAX      TBgpInstanceAddPathEntry
    MAX-ACCESS  not-accessible
    STATUS      current
    DESCRIPTION
        "An entry (conceptual row) in the tBgpInstanceAddPathTable.

         An entry is created when an entry in tBgpInstanceEntry is. When
         created, all objects are initialized to their default values."
    AUGMENTS    { tBgpInstanceEntry }
    ::= { tBgpInstanceAddPathTable 1 }

TBgpInstanceAddPathEntry         ::= SEQUENCE
{
    tBgpInstanceAddPathEnable        TruthValue,
    tBgpInstanceAddPathRecv          TmnxAddPathAddressFamily,
    tBgpInstanceAddPathIpv4Limit     TmnxAddPathSendLimit,
    tBgpInstanceAddPathVpnIpv4Limit  TmnxAddPathSendLimit,
    tBgpInstanceAddPathIpv6Limit     TmnxAddPathSendLimit,
    tBgpInstanceAddPathVpnIpv6Limit  TmnxAddPathSendLimit,
    tBgpInstanceAddPathLblIpv4Limit  TmnxAddPathSendLimit,
    tBgpInstanceAddPathLblIpv6Limit  TmnxAddPathSendLimit,
    tBgpInstanceAddPathMvpnIpv4Limit Integer32,
    tBgpInstanceAddPathMvpnIpv6Limit Integer32,
    tBgpInstanceAddPathMCVpnV4Limit  Integer32,
    tBgpInstanceAddPathMCVpnV6Limit  Integer32,
    tBgpInstanceAddPathEvpnLimit     TmnxAddPathSendLimit
}

tBgpInstanceAddPathEnable        OBJECT-TYPE
    SYNTAX      TruthValue
    MAX-ACCESS  read-create
    STATUS      current
    DESCRIPTION
        "The value of tBgpInstanceAddPathEnable specifies whether the BGP
         ADD-PATH send capability is enabled on this BGP instance.

         ADD-PATH allows a BGP router to advertise multiple distinct paths for
         the same prefix/NLRI(Network Layer Reachability Information). This
         capability provides a number of potential benefits like reduced
         routing churn, faster convergence, better loadsharing etc.

         When the value of tBgpInstanceAddPathEnable is set to 'true', the BGP
         ADD-PATH send limit objects tBgpInstanceAddPathIpv4Limit,
         tBgpInstanceAddPathVpnIpv4Limit, tBgpInstanceAddPathIpv6Limit,
         tBgpInstanceAddPathVpnIpv6Limit, tBgpInstanceAddPathLblIpv4Limit, and
         tBgpInstanceAddPathLblIpv6Limit represent their assigned values.

         The default value of tBgpInstanceAddPathEnable is 'false', which means
         the ADD-PATH capability is disabled on this BGP instance and the
         values of the BGP ADD-PATH send limit objects are not valid."
    DEFVAL      { false }
    ::= { tBgpInstanceAddPathEntry 1 }

tBgpInstanceAddPathRecv          OBJECT-TYPE
    SYNTAX      TmnxAddPathAddressFamily
    MAX-ACCESS  read-create
    STATUS      current
    DESCRIPTION
        "The value of tBgpInstanceAddPathRecv specifies the address families
         which are enabled to receive BGP ADD-PATH.

         ADD-PATH allows a BGP router to receive multiple distinct paths for
         the same prefix/NLRI (Network Layer Reachability Information)."
    DEFVAL      { {none} }
    ::= { tBgpInstanceAddPathEntry 2 }

tBgpInstanceAddPathIpv4Limit     OBJECT-TYPE
    SYNTAX      TmnxAddPathSendLimit
    MAX-ACCESS  read-create
    STATUS      current
    DESCRIPTION
        "The value of tBgpInstanceAddPathIpv4Limit specifies the maximum number
         of paths per IPv4 prefix that can be advertised to ADD-PATH peers.

         An 'inconsistentValue' error is returned if an attempt is made to set
         this object to a value greater than tBgpInstanceMultipathBgp."
    DEFVAL      { 0 }
    ::= { tBgpInstanceAddPathEntry 3 }

tBgpInstanceAddPathVpnIpv4Limit  OBJECT-TYPE
    SYNTAX      TmnxAddPathSendLimit
    MAX-ACCESS  read-create
    STATUS      current
    DESCRIPTION
        "The value of tBgpInstanceAddPathVpnIpv4Limit specifies the maximum
         number of paths per VPN IPv4 prefix that can be advertised to ADD-PATH
         peers.

         An 'inconsistentValue' error is returned if an attempt is made to set
         this object to a value greater than tBgpInstanceMultipathBgp."
    DEFVAL      { 0 }
    ::= { tBgpInstanceAddPathEntry 4 }

tBgpInstanceAddPathIpv6Limit     OBJECT-TYPE
    SYNTAX      TmnxAddPathSendLimit
    MAX-ACCESS  read-create
    STATUS      current
    DESCRIPTION
        "The value of tBgpInstanceAddPathIpv6Limit specifies the maximum number
         of paths per IPv6 prefix that can be advertised to ADD-PATH peers.

         An 'inconsistentValue' error is returned if an attempt is made to set
         this object to a value greater than tBgpInstanceMultipathBgp."
    DEFVAL      { 0 }
    ::= { tBgpInstanceAddPathEntry 5 }

tBgpInstanceAddPathVpnIpv6Limit  OBJECT-TYPE
    SYNTAX      TmnxAddPathSendLimit
    MAX-ACCESS  read-create
    STATUS      current
    DESCRIPTION
        "The value of tBgpInstanceAddPathVpnIpv6Limit specifies the maximum
         number of paths per VPN IPv6 prefix that can be advertised to ADD-PATH
         peers.

         An 'inconsistentValue' error is returned if an attempt is made to set
         this object to a value greater than tBgpInstanceMultipathBgp."
    DEFVAL      { 0 }
    ::= { tBgpInstanceAddPathEntry 6 }

tBgpInstanceAddPathLblIpv4Limit  OBJECT-TYPE
    SYNTAX      TmnxAddPathSendLimit
    MAX-ACCESS  read-create
    STATUS      current
    DESCRIPTION
        "The value of tBgpInstanceAddPathLblIpv4Limit specifies the maximum
         number of paths per label IPv4 prefix that can be advertised to
         ADD-PATH peers.

         An 'inconsistentValue' error is returned if an attempt is made to set
         this object to a value greater than tBgpInstanceMultipathBgp."
    DEFVAL      { 0 }
    ::= { tBgpInstanceAddPathEntry 7 }

tBgpInstanceAddPathLblIpv6Limit  OBJECT-TYPE
    SYNTAX      TmnxAddPathSendLimit
    MAX-ACCESS  read-create
    STATUS      current
    DESCRIPTION
        "The value of tBgpInstanceAddPathLblIpv6Limit specifies the maximum
         number of paths per label IPv6 prefix that can be advertised to
         ADD-PATH peers.

         An 'inconsistentValue' error is returned if an attempt is made to set
         this object to a value greater than tBgpInstanceMultipathBgp."
    DEFVAL      { 0 }
    ::= { tBgpInstanceAddPathEntry 8 }

tBgpInstanceAddPathMvpnIpv4Limit OBJECT-TYPE
    SYNTAX      Integer32 (0..16)
    MAX-ACCESS  read-create
    STATUS      current
    DESCRIPTION
        "The value of tBgpInstanceAddPathMvpnIpv4Limit specifies the maximum
         number of paths per mvpn IPv4 prefix that can be advertised to
         ADD-PATH peers.

         An 'inconsistentValue' error is returned if an attempt is made to set
         this object to a value greater than tBgpInstanceMultipathBgp."
    DEFVAL      { 0 }
    ::= { tBgpInstanceAddPathEntry 9 }

tBgpInstanceAddPathMvpnIpv6Limit OBJECT-TYPE
    SYNTAX      Integer32 (0..16)
    MAX-ACCESS  read-create
    STATUS      current
    DESCRIPTION
        "The value of tBgpInstanceAddPathMvpnIpv6Limit specifies the maximum
         number of paths per mvpn IPv6 prefix that can be advertised to
         ADD-PATH peers.

         An 'inconsistentValue' error is returned if an attempt is made to set
         this object to a value greater than tBgpInstanceMultipathBgp."
    DEFVAL      { 0 }
    ::= { tBgpInstanceAddPathEntry 10 }

tBgpInstanceAddPathMCVpnV4Limit  OBJECT-TYPE
    SYNTAX      Integer32 (0..16)
    MAX-ACCESS  read-create
    STATUS      current
    DESCRIPTION
        "The value of tBgpInstanceAddPathMCVpnV4Limit specifies the maximum
         number of paths per Mcast VPN IPv4 prefix that can be advertised to
         ADD-PATH peers.

         An 'inconsistentValue' error is returned if an attempt is made to set
         this object to a value greater than tBgpInstanceMultipathBgp."
    DEFVAL      { 0 }
    ::= { tBgpInstanceAddPathEntry 11 }

tBgpInstanceAddPathMCVpnV6Limit  OBJECT-TYPE
    SYNTAX      Integer32 (0..16)
    MAX-ACCESS  read-create
    STATUS      current
    DESCRIPTION
        "The value of tBgpInstanceAddPathMCVpnV6Limit specifies the maximum
         number of paths per Mcast VPN IPv6 prefix that can be advertised to
         ADD-PATH peers.

         An 'inconsistentValue' error is returned if an attempt is made to set
         this object to a value greater than tBgpInstanceMultipathBgp."
    DEFVAL      { 0 }
    ::= { tBgpInstanceAddPathEntry 12 }

tBgpInstanceAddPathEvpnLimit     OBJECT-TYPE
    SYNTAX      TmnxAddPathSendLimit
    MAX-ACCESS  read-create
    STATUS      current
    DESCRIPTION
        "The value of tBgpInstanceAddPathEvpnLimit specifies the maximum number
         of paths per Mcast VPN IPv6 prefix that can be advertised to ADD-PATH
         peers.

         An 'inconsistentValue' error is returned if an attempt is made to set
         this object to a value greater than tBgpInstanceMultipathBgp."
    DEFVAL      { 0 }
    ::= { tBgpInstanceAddPathEntry 13 }

tBgpInstanceParamsExtTblLstCh    OBJECT-TYPE
    SYNTAX      TimeStamp
    MAX-ACCESS  read-only
    STATUS      current
    DESCRIPTION
        "The value of tBgpInstanceParamsExtTblLstCh indicates the timestamp
         when an entry in the tBgpInstanceParamsExtTable was last changed."
    ::= { tBgpInstanceObjects 23 }

tBgpInstanceParamsExtTable       OBJECT-TYPE
    SYNTAX      SEQUENCE OF TBgpInstanceParamsExtEntry
    MAX-ACCESS  not-accessible
    STATUS      current
    DESCRIPTION
        "The tBgpInstanceParamsExtTable consists of information about the
         attributes configured for the BGP instance.

         The table entries are indexed by BGP instance."
    ::= { tBgpInstanceObjects 24 }

tBgpInstanceParamsExtEntry       OBJECT-TYPE
    SYNTAX      TBgpInstanceParamsExtEntry
    MAX-ACCESS  not-accessible
    STATUS      current
    DESCRIPTION
        "An entry (conceptual row) in the tBgpInstanceParamsExtTable.

         An entry is created when an entry in tBgpInstanceEntry is. Each entry
         maintains the attributes configured for BGP instance. When created,
         all objects are initialized to their default values."
    AUGMENTS    { tBgpInstanceEntry }
    ::= { tBgpInstanceParamsExtTable 1 }

TBgpInstanceParamsExtEntry       ::= SEQUENCE
{
    tBgpInstanceEnforceFirstAS       TruthValue,
    tBgpInstanceLLGRAdvStaleTime     Unsigned32,
    tBgpInstanceLLGROvrideStaleTime  Unsigned32,
    tBgpInstanceLLGROvrideResTime    Unsigned32,
    tBgpInstanceLLGRFwdingBitsSet    INTEGER,
    tBgpInstanceLLGRAdvStaleToNeigh  TruthValue,
    tBgpInstLLGRAdvToNeighWthoutNoEx TruthValue,
    tBgpInstanceLLGR                 TruthValue,
    tBgpInstanceAdvIpv6NhFamily      TmnxIpFamily,
    tBgpInstanceExtendNhEncoding     TmnxIpFamily,
    tBgpInstanceBypassMRAITimer      TruthValue,
    tBgpInstanceDisableLargeComms    TruthValue,
    tBgpInstanceImportSrPolicy       TruthValue,
    tBgpInstanceEnfNbrTrust          TmnxIpFamily,
    tBgpInstanceLoopDetectThreshold  Unsigned32,
    tBgpInstanceAllowUnresLeaking    TruthValue,
    tBgpInstanceConvMinWaitToAdv     Unsigned32,
    tBgpInstanceSendExportPolicy     TLPolicyNameOrExpOrEmpty,
    tBgpInstEbgpPreference           TmnxBgpPreference,
    tBgpInstIbgpPreference           TmnxBgpPreference,
    tBgpInstEbgpLabelPreference      TmnxBgpPreference,
    tBgpInstIbgpLabelPreference      TmnxBgpPreference,
    tBgpInstEBGPRejWithoutPlcyImpt   TruthValue,
    tBgpInstEBGPRejWithoutPlcyExpt   TruthValue,
    tBgpInstRemovePrivateReplaceAS   TruthValue,
    tBgpInstBlockPrefixSID           TruthValue,
    tBgpInstDefOriginate             TmnxIpFamily,
    tBgpInstTcpMss                   Unsigned32,
    tBgpPrefixSidRangeType           INTEGER,
    tBgpPrefixSidRangeStartLabel     TmnxPrefixSidFullRange,
    tBgpPrefixSidRangeMaxIdx         TmnxPrefixSidFullRange,
    tBgpSrAdminState                 TmnxAdminState,
    tBgpSegmentRouting               TruthValue,
    tBgpDisableExplicitNull          TruthValue,
    tBgpSelLabelIpv4Inst             TruthValue,
    tBgpInstBgpTunnelMetric          Unsigned32,
    tBgpInstBgpTunnelMetricPrefAigp  TruthValue,
    tBgpEgressEng                    TruthValue,
    tBgpEgressEngShutdown            TmnxAdminState,
    tBgpInstanceNHResVpnFamPolicy    TLPolicyStatementNameOrEmpty,
    tBgpInstBgpTunnelPreference      TmnxBgpPreference,
    tBgpInstLabelIpv6ExplicitNull    TruthValue,
    tBgpSegmentRoutingV6             TruthValue,
    tBgpInstSrv6SourceAddrType       InetAddressType,
    tBgpInstSrv6SourceAddr           InetAddress,
    tBgpInstanceSubconfVpnFwding     TruthValue,
    tBgpInstanceSelLblIpPri          TruthValue,
    tBgpInstanceDomainId             TmnxDPathDomainId,
    tBgpInstanceDpathLgthIgnr        TruthValue,
    tBgpInstanceNHPreferTransportFrr TruthValue,
    tBgpInstBgpTunnelMetricPrefMed   TruthValue,
    tBgpInstanceSelLabelIp           INTEGER,
    tBgpInstanceBfdStrictAdvertise   TruthValue,
    tBgpInstanceBfdStrictNhReach     TruthValue,
    tBgpInstanceBfdStrictHoldTime    Unsigned32,
    tBgpInstanceAttrSetRemove        TruthValue,
    tBgpInstLegacyFaultTolerance     TruthValue
}

tBgpInstanceEnforceFirstAS       OBJECT-TYPE
    SYNTAX      TruthValue
    MAX-ACCESS  read-create
    STATUS      current
    DESCRIPTION
        "The value of tBgpInstanceEnforceFirstAS specifies whether the receipt
         of BGP routes from an eBGP neighbor should be classified as an error
         when it has an AS-Path with the most recent AS not matching the
         configured peer-as of the neighbor.

         If the value is set to 'true', the most recent AS number in the
         AS-Path will be checked for every received route from the peer or set
         of peers to match the peer's configured peer-as. If it does not match,
         then the session will be reset if the update-fault-tolerance under
         error-handling is not configured. Else, the session will not be reset,
         but all the prefixes in the received update will be treated as
         withdrawn and logged.

         It is applicable to all the address families and only to true eBGP
         sessions."
    DEFVAL      { false }
    ::= { tBgpInstanceParamsExtEntry 1 }

tBgpInstanceLLGRAdvStaleTime     OBJECT-TYPE
    SYNTAX      Unsigned32 (0..16777215)
    UNITS       "seconds"
    MAX-ACCESS  read-create
    STATUS      current
    DESCRIPTION
        "The value of tBgpInstanceLLGRAdvStaleTime specifies the time value
         until when a route can be used after the session with the peer is
         disconnected"
    DEFVAL      { 86400 }
    ::= { tBgpInstanceParamsExtEntry 2 }

tBgpInstanceLLGROvrideStaleTime  OBJECT-TYPE
    SYNTAX      Unsigned32 (0..16777216)
    UNITS       "seconds"
    MAX-ACCESS  read-create
    STATUS      current
    DESCRIPTION
        "The value of tBgpInstanceLLGROvrideStaleTime specifies the stale time
         for the BGP session when it is in helper mode."
    DEFVAL      { 16777216 }
    ::= { tBgpInstanceParamsExtEntry 3 }

tBgpInstanceLLGROvrideResTime    OBJECT-TYPE
    SYNTAX      Unsigned32 (0..4096)
    UNITS       "seconds"
    MAX-ACCESS  read-create
    STATUS      current
    DESCRIPTION
        "The value of tBgpInstanceLLGROvrideResTime specifies the restart time
         for the BGP session when it is in helper mode."
    DEFVAL      { 4096 }
    ::= { tBgpInstanceParamsExtEntry 4 }

tBgpInstanceLLGRFwdingBitsSet    OBJECT-TYPE
    SYNTAX      INTEGER {
        none    (0),
        all     (1),
        non-fwd (2)
    }
    MAX-ACCESS  read-create
    STATUS      current
    DESCRIPTION
        "The value of tBgpInstanceLLGRFwdingBitsSet specifies the behaviour of
         the F bit for each AFI/SAFI."
    DEFVAL      { none }
    ::= { tBgpInstanceParamsExtEntry 5 }

tBgpInstanceLLGRAdvStaleToNeigh  OBJECT-TYPE
    SYNTAX      TruthValue
    MAX-ACCESS  read-create
    STATUS      current
    DESCRIPTION
        "The value of tBgpInstanceLLGRAdvStaleToNeigh decides whether to
         withdraw the route towards eBGP peers that did not advertise the LLGR
         capability and re-advertise to all other peers with the addition of
         the LLGR_STALE community."
    DEFVAL      { false }
    ::= { tBgpInstanceParamsExtEntry 6 }

tBgpInstLLGRAdvToNeighWthoutNoEx OBJECT-TYPE
    SYNTAX      TruthValue
    MAX-ACCESS  read-create
    STATUS      current
    DESCRIPTION
        "The value of tBgpInstLLGRAdvToNeighWthoutNoEx decides whether to
         advertise the route to all peers with the addition of the LLGR_STALE
         community.

         This can be configured only when tBgpInstanceLLGRAdvStaleToNeigh is
         configured on the system."
    DEFVAL      { false }
    ::= { tBgpInstanceParamsExtEntry 7 }

tBgpInstanceLLGR                 OBJECT-TYPE
    SYNTAX      TruthValue
    MAX-ACCESS  read-create
    STATUS      current
    DESCRIPTION
        "The value of tBgpInstanceLLGR specifies whether or not long lived
         graceful restart capabilities are enabled on this instance of BGP.

         When the value is set to 'false' long lived graceful restart is
         disabled and any previous configuration of other long lived graceful
         restart parameters is removed."
    DEFVAL      { false }
    ::= { tBgpInstanceParamsExtEntry 8 }

tBgpInstanceAdvIpv6NhFamily      OBJECT-TYPE
    SYNTAX      TmnxIpFamily
    MAX-ACCESS  read-create
    STATUS      current
    DESCRIPTION
        "The value of tBgpInstanceAdvIpv6NhFamily specifies the types of
         AFI/SAFI the SROS BGP supports extended next-hop encoding and
         resolution."
    ::= { tBgpInstanceParamsExtEntry 9 }

tBgpInstanceExtendNhEncoding     OBJECT-TYPE
    SYNTAX      TmnxIpFamily
    MAX-ACCESS  read-create
    STATUS      current
    DESCRIPTION
        "The value of tBgpInstanceExtendNhEncoding specifies the types of
         AFI/SAFI the Bgp instance is configured to support extended next-hop
         encoding."
    ::= { tBgpInstanceParamsExtEntry 10 }

tBgpInstanceBypassMRAITimer      OBJECT-TYPE
    SYNTAX      TruthValue
    MAX-ACCESS  read-create
    STATUS      current
    DESCRIPTION
        "The value of tBgpInstanceBypassMRAITimer specifies whether the Bgp
         instance is configured to send out the BGP update immediately after
         the session comes up, without waiting for Minimum Route Advertisement
         Interval, tBgpInstanceMinRouteAdvertisement, to countdown to zero.

         If the value is set to 'true', tBgpInstanceMinRouteAdvertisement's
         value is disregarded and BGP updates are sent out immediately after
         the session comes up.

         If the value is set to 'false', the system waits for
         tBgpInstanceMinRouteAdvertisement's full value to countdown before
         sending out the BGP updates after the session comes up."
    DEFVAL      { false }
    ::= { tBgpInstanceParamsExtEntry 11 }

tBgpInstanceDisableLargeComms    OBJECT-TYPE
    SYNTAX      TruthValue
    MAX-ACCESS  read-create
    STATUS      current
    DESCRIPTION
        "The value of tBgpInstanceDisableLargeComms enables or disables sending
         of community attribute to the peer for large communities."
    DEFVAL      { false }
    ::= { tBgpInstanceParamsExtEntry 12 }

tBgpInstanceImportSrPolicy       OBJECT-TYPE
    SYNTAX      TruthValue
    MAX-ACCESS  read-create
    STATUS      current
    DESCRIPTION
        "The value of tBgpInstanceImportSrPolicy enables or disables import of
         sr-policy for use in resolving next-hop."
    DEFVAL      { false }
    ::= { tBgpInstanceParamsExtEntry 13 }

tBgpInstanceEnfNbrTrust          OBJECT-TYPE
    SYNTAX      TmnxIpFamily
    MAX-ACCESS  read-create
    STATUS      current
    DESCRIPTION
        "The value of tBgpInstanceEnfNbrTrust specifies the address families on
         which ILM forwarding behavior is enabled."
    DEFVAL      { {} }
    ::= { tBgpInstanceParamsExtEntry 14 }

tBgpInstanceLoopDetectThreshold  OBJECT-TYPE
    SYNTAX      Unsigned32 (0..15)
    MAX-ACCESS  read-create
    STATUS      current
    DESCRIPTION
        "The value of tBgpInstanceLoopDetectThreshold specifies the occurrence
         of the global ASN when exceeded triggers the loop-detect behavior."
    DEFVAL      { 0 }
    ::= { tBgpInstanceParamsExtEntry 15 }

tBgpInstanceAllowUnresLeaking    OBJECT-TYPE
    SYNTAX      TruthValue
    MAX-ACCESS  read-create
    STATUS      current
    DESCRIPTION
        "The value of tBgpInstanceAllowUnresLeaking specifies whether  or not a
         VPRN can import a route."
    DEFVAL      { false }
    ::= { tBgpInstanceParamsExtEntry 16 }

tBgpInstanceConvMinWaitToAdv     OBJECT-TYPE
    SYNTAX      Unsigned32 (0..3600)
    UNITS       "seconds"
    MAX-ACCESS  read-create
    STATUS      current
    DESCRIPTION
        "The value of tBgpInstanceConvMinWaitToAdv specifies the timer value
         for which no routes are advertised."
    DEFVAL      { 0 }
    ::= { tBgpInstanceParamsExtEntry 17 }

tBgpInstanceSendExportPolicy     OBJECT-TYPE
    SYNTAX      TLPolicyNameOrExpOrEmpty
    MAX-ACCESS  read-create
    STATUS      current
    DESCRIPTION
        "The value of tBgpInstanceSendExportPolicy specifies the send default
         export policy."
    DEFVAL      { "" }
    ::= { tBgpInstanceParamsExtEntry 18 }

tBgpInstEbgpPreference           OBJECT-TYPE
    SYNTAX      TmnxBgpPreference (0..255)
    MAX-ACCESS  read-create
    STATUS      current
    DESCRIPTION
        "The value of tBgpInstEbgpPreference specifies the route preference for
         ebgp routes."
    DEFVAL      { 0 }
    ::= { tBgpInstanceParamsExtEntry 19 }

tBgpInstIbgpPreference           OBJECT-TYPE
    SYNTAX      TmnxBgpPreference (0..255)
    MAX-ACCESS  read-create
    STATUS      current
    DESCRIPTION
        "The value of tBgpInstIbgpPreference specifies the route preference for
         ibgp routes."
    DEFVAL      { 0 }
    ::= { tBgpInstanceParamsExtEntry 20 }

tBgpInstEbgpLabelPreference      OBJECT-TYPE
    SYNTAX      TmnxBgpPreference (0..255)
    MAX-ACCESS  read-create
    STATUS      current
    DESCRIPTION
        "The value of tBgpInstEbgpLabelPreference specifies the route
         preference for label-IPv4 and label-IPv6 ebgp routes."
    DEFVAL      { 0 }
    ::= { tBgpInstanceParamsExtEntry 21 }

tBgpInstIbgpLabelPreference      OBJECT-TYPE
    SYNTAX      TmnxBgpPreference (0..255)
    MAX-ACCESS  read-create
    STATUS      current
    DESCRIPTION
        "The value of tBgpInstIbgpLabelPreference specifies the route
         preference for label-IPv4 and label-IPv6 ibgp routes."
    DEFVAL      { 0 }
    ::= { tBgpInstanceParamsExtEntry 22 }

tBgpInstEBGPRejWithoutPlcyImpt   OBJECT-TYPE
    SYNTAX      TruthValue
    MAX-ACCESS  read-create
    STATUS      current
    DESCRIPTION
        "The value of tBgpInstEBGPRejWithoutPlcyImpt enables or disables if
         policies can be imported."
    DEFVAL      { false }
    ::= { tBgpInstanceParamsExtEntry 23 }

tBgpInstEBGPRejWithoutPlcyExpt   OBJECT-TYPE
    SYNTAX      TruthValue
    MAX-ACCESS  read-create
    STATUS      current
    DESCRIPTION
        "The value of tBgpInstEBGPRejWithoutPlcyExpt enables or disables if
         policies can be exported."
    DEFVAL      { false }
    ::= { tBgpInstanceParamsExtEntry 24 }

tBgpInstRemovePrivateReplaceAS   OBJECT-TYPE
    SYNTAX      TruthValue
    MAX-ACCESS  read-create
    STATUS      current
    DESCRIPTION
        "The value of tBgpInstRemovePrivateReplaceAS specifies if private AS
         numbers in the AS Path should be replaced with the configured global
         AS before advertising them to BGP peers."
    DEFVAL      { false }
    ::= { tBgpInstanceParamsExtEntry 25 }

tBgpInstBlockPrefixSID           OBJECT-TYPE
    SYNTAX      TruthValue
    MAX-ACCESS  read-create
    STATUS      current
    DESCRIPTION
        "The value of tBgpInstBlockPrefixSID enables or disables sending of the
          prefix SID attribute."
    DEFVAL      { false }
    ::= { tBgpInstanceParamsExtEntry 26 }

tBgpInstDefOriginate             OBJECT-TYPE
    SYNTAX      TmnxIpFamily
    MAX-ACCESS  read-create
    STATUS      current
    DESCRIPTION
        "The value of tBgpInstDefOriginate specifies the types of AFI/SAFI for
         which SROS BGP will originate default route independent of the RTM
         default route"
    ::= { tBgpInstanceParamsExtEntry 27 }

tBgpInstTcpMss                   OBJECT-TYPE
    SYNTAX      Unsigned32 (0 | 384..9746)
    MAX-ACCESS  read-create
    STATUS      current
    DESCRIPTION
        "The value of tBgpInstTcpMss specifies the TCP maximum segment
         size(MSS). When the value of tBgpInstTcpMss is set to 0, the command
         removes the static value and allows the TCP MSS value to be calculated
         based on the IP MTU value."
    DEFVAL      { 0 }
    ::= { tBgpInstanceParamsExtEntry 28 }

tBgpPrefixSidRangeType           OBJECT-TYPE
    SYNTAX      INTEGER {
        none   (0),
        global (1),
        local  (2)
    }
    MAX-ACCESS  read-create
    STATUS      current
    DESCRIPTION
        "The value of tBgpPrefixSidRangeType specifies whether global
         or  operation mode is selected. If local mode is used,
         tBgpPrefixSidRangeStartLabel and tBgpPrefixSidRangeMaxIdx
         describe the range. If global mode is selected those fields are
         not used. "
    DEFVAL      { none }
    ::= { tBgpInstanceParamsExtEntry 29 }

tBgpPrefixSidRangeStartLabel     OBJECT-TYPE
    SYNTAX      TmnxPrefixSidFullRange
    MAX-ACCESS  read-create
    STATUS      current
    DESCRIPTION
        "The value of tBgpPrefixSidRangeStartLabel specifies the local label
         starting offset value."
    DEFVAL      { 0 }
    ::= { tBgpInstanceParamsExtEntry 30 }

tBgpPrefixSidRangeMaxIdx         OBJECT-TYPE
    SYNTAX      TmnxPrefixSidFullRange
    MAX-ACCESS  read-create
    STATUS      current
    DESCRIPTION
        "The value of tBgpPrefixSidRangeMaxIdx specifies the maximum local SID
         index that can be used."
    DEFVAL      { 1 }
    ::= { tBgpInstanceParamsExtEntry 31 }

tBgpSrAdminState                 OBJECT-TYPE
    SYNTAX      TmnxAdminState
    MAX-ACCESS  read-create
    STATUS      current
    DESCRIPTION
        "The value of the object tBgpSrAdminState specifies the desired
         administrative state of Segment Routing for this BGP instance."
    DEFVAL      { outOfService }
    ::= { tBgpInstanceParamsExtEntry 32 }

tBgpSegmentRouting               OBJECT-TYPE
    SYNTAX      TruthValue
    MAX-ACCESS  read-create
    STATUS      current
    DESCRIPTION
        "The value of tBgpSegmentRouting specifies whether or not segment
         routing capabilities are enabled on this instance of BGP.

         When the value is set to 'false' segment routing is disabled and  any
         previous configuration of other segment routing parameters  is
         removed."
    DEFVAL      { false }
    ::= { tBgpInstanceParamsExtEntry 33 }

tBgpDisableExplicitNull          OBJECT-TYPE
    SYNTAX      TruthValue
    MAX-ACCESS  read-create
    STATUS      current
    DESCRIPTION
        "The value of tBgpDisableExplicitNull specifies whether or not
         advertised label and associated programming rules are enabled  on this
         instance of BGP."
    DEFVAL      { false }
    ::= { tBgpInstanceParamsExtEntry 34 }

tBgpSelLabelIpv4Inst             OBJECT-TYPE
    SYNTAX      TruthValue
    MAX-ACCESS  read-create
    STATUS      current
    DESCRIPTION
        "The value of tBgpSelLabelIpv4Inst specifies whether to enable/disable
         selective download of label-ipv4 routes"
    DEFVAL      { false }
    ::= { tBgpInstanceParamsExtEntry 35 }

tBgpInstBgpTunnelMetric          OBJECT-TYPE
    SYNTAX      Unsigned32
    MAX-ACCESS  read-create
    STATUS      current
    DESCRIPTION
        "The value of tBgpInstBgpTunnelMetric determines the metric of the
         route installed in RTM"
    DEFVAL      { 1000 }
    ::= { tBgpInstanceParamsExtEntry 36 }

tBgpInstBgpTunnelMetricPrefAigp  OBJECT-TYPE
    SYNTAX      TruthValue
    MAX-ACCESS  read-create
    STATUS      current
    DESCRIPTION
        "If tBgpInstBgpTunnelMetricPrefAigp is enabled the metric of the route
         installed in RTM is the aigp-metric of the route if no aigp-metric is
         available the value of tBgpInstBgpTunnelMetric is used"
    DEFVAL      { false }
    ::= { tBgpInstanceParamsExtEntry 37 }

tBgpEgressEng                    OBJECT-TYPE
    SYNTAX      TruthValue
    MAX-ACCESS  read-create
    STATUS      current
    DESCRIPTION
        "The value of tBgpEgressEng specifies whether to enable/disable  egress
         peer engineering"
    DEFVAL      { false }
    ::= { tBgpInstanceParamsExtEntry 38 }

tBgpEgressEngShutdown            OBJECT-TYPE
    SYNTAX      TmnxAdminState
    MAX-ACCESS  read-create
    STATUS      current
    DESCRIPTION
        "The value of the object tBgpEgressEngShutdown specifies the desired
         administrative state of Egress Engineering for this BGP instance."
    DEFVAL      { outOfService }
    ::= { tBgpInstanceParamsExtEntry 39 }

tBgpInstanceNHResVpnFamPolicy    OBJECT-TYPE
    SYNTAX      TLPolicyStatementNameOrEmpty
    MAX-ACCESS  read-create
    STATUS      current
    DESCRIPTION
        "The value of tBgpInstanceNHResVpnFamPolicy specifies the policy to be
         applied for filtering the routes to be considered for next-hop
         resolution process."
    DEFVAL      { "" }
    ::= { tBgpInstanceParamsExtEntry 40 }

tBgpInstBgpTunnelPreference      OBJECT-TYPE
    SYNTAX      TmnxBgpPreference (1..255)
    MAX-ACCESS  read-create
    STATUS      current
    DESCRIPTION
        "The value of tBgpInstBgpTunnelPreference determines the preference of
         the route installed in RTM"
    DEFVAL      { 12 }
    ::= { tBgpInstanceParamsExtEntry 41 }

tBgpInstLabelIpv6ExplicitNull    OBJECT-TYPE
    SYNTAX      TruthValue
    MAX-ACCESS  read-create
    STATUS      current
    DESCRIPTION
        "The value of tBgpInstLabelIpv6ExplicitNull specifies whether the route
          can resolve the next-hop, and that route itself is resolved by a
         non-BGP route in RTM or a tunnel in TTM."
    DEFVAL      { false }
    ::= { tBgpInstanceParamsExtEntry 42 }

tBgpSegmentRoutingV6             OBJECT-TYPE
    SYNTAX      TruthValue
    MAX-ACCESS  read-create
    STATUS      current
    DESCRIPTION
        "The value of tBgpSegmentRoutingV6 specifies whether or not segment
         routing V6 capabilities are enabled on this instance of BGP.

         When the value is set to 'false' segment routing V6 is disabled and
         any previous configuration of other segment routing parameters  is
         removed."
    DEFVAL      { false }
    ::= { tBgpInstanceParamsExtEntry 43 }

tBgpInstSrv6SourceAddrType       OBJECT-TYPE
    SYNTAX      InetAddressType
    MAX-ACCESS  read-create
    STATUS      current
    DESCRIPTION
        "The value of tBgpInstSrv6SourceAddrType specifies the type of
         tBgpInstSrv6SourceAddr."
    DEFVAL      { unknown }
    ::= { tBgpInstanceParamsExtEntry 44 }

tBgpInstSrv6SourceAddr           OBJECT-TYPE
    SYNTAX      InetAddress (SIZE (0|16))
    MAX-ACCESS  read-create
    STATUS      current
    DESCRIPTION
        "The value of tBgpInstSrv6SourceAddr specifies the source address."
    DEFVAL      { ''H }
    ::= { tBgpInstanceParamsExtEntry 45 }

tBgpInstanceSubconfVpnFwding     OBJECT-TYPE
    SYNTAX      TruthValue
    MAX-ACCESS  read-create
    STATUS      current
    DESCRIPTION
        "The value of tBgpInstanceSubconfVpnFwding specifies whether a
         route-reflector will resolve VPN-IPv4 and VPN-IPv6 routes."
    DEFVAL      { false }
    ::= { tBgpInstanceParamsExtEntry 46 }

tBgpInstanceSelLblIpPri          OBJECT-TYPE
    SYNTAX      TruthValue
    MAX-ACCESS  read-create
    STATUS      current
    DESCRIPTION
        "The value of tBgpInstanceSelLblIpPri specifies whether in  base router
         BGP instance every received label-ipv4 and  label-ipv6 RIB-IN that is
         potentially usable by a local service  is automatically tagged as
         high-priority, unless there is an  import policy that has processed
         the RIB-IN and explicitly  assigned it a normal priority."
    DEFVAL      { false }
    ::= { tBgpInstanceParamsExtEntry 47 }

tBgpInstanceDomainId             OBJECT-TYPE
    SYNTAX      TmnxDPathDomainId
    MAX-ACCESS  read-create
    STATUS      obsolete
    DESCRIPTION
        "The value of tBgpInstanceDomainId specifies the Domain ID used in D-Path for routes advertisement
          BGP vprn service."
    DEFVAL      { '000000000000'H }
    ::= { tBgpInstanceParamsExtEntry 48 }

tBgpInstanceDpathLgthIgnr        OBJECT-TYPE
    SYNTAX      TruthValue
    MAX-ACCESS  read-create
    STATUS      current
    DESCRIPTION
        "The value of tBgpInstanceDpathLgthIgnr specifies if BGP ignores the
         D-PATH domain segment length  for best path selection."
    DEFVAL      { false }
    ::= { tBgpInstanceParamsExtEntry 49 }

tBgpInstanceNHPreferTransportFrr OBJECT-TYPE
    SYNTAX      TruthValue
    MAX-ACCESS  read-create
    STATUS      current
    DESCRIPTION
        ""
    DEFVAL      { false }
    ::= { tBgpInstanceParamsExtEntry 50 }

tBgpInstBgpTunnelMetricPrefMed   OBJECT-TYPE
    SYNTAX      TruthValue
    MAX-ACCESS  read-create
    STATUS      current
    DESCRIPTION
        "If tBgpInstBgpTunnelMetricPrefMed is enabled the metric of the route
         installed in the tunnel-table is the med-metric of the route if no
         med-metric is available the value of tBgpInstBgpTunnelMetric is used"
    DEFVAL      { false }
    ::= { tBgpInstanceParamsExtEntry 52 }

tBgpInstanceSelLabelIp           OBJECT-TYPE
    SYNTAX      INTEGER {
        none                     (0),
        no-install               (1),
        route-table-install-only (2)
    }
    MAX-ACCESS  read-create
    STATUS      current
    DESCRIPTION
        "The value of tBgpInstanceSelLabelIp specifies the behaviour on how to
         install label ip routes."
    DEFVAL      { none }
    ::= { tBgpInstanceParamsExtEntry 53 }

tBgpInstanceBfdStrictAdvertise   OBJECT-TYPE
    SYNTAX      TruthValue
    MAX-ACCESS  read-create
    STATUS      current
    DESCRIPTION
        "The value of tBgpInstanceBfdStrictAdvertise specifies whether strict
         Bi-directional Forwarding Detection will be advertised by this router.

         When the value is 'true', strict BFD mode capability is announced by
         this router"
    DEFVAL      { false }
    ::= { tBgpInstanceParamsExtEntry 54 }

tBgpInstanceBfdStrictNhReach     OBJECT-TYPE
    SYNTAX      TruthValue
    MAX-ACCESS  read-create
    STATUS      current
    DESCRIPTION
        "The value of tBgpInstanceBfdStrictNhReach specifies whether strict BFD
         mode will be used for next-hop reachability.

         When the value is 'true', the strict BFD state will be applied to the
         BGP next-hop"
    DEFVAL      { false }
    ::= { tBgpInstanceParamsExtEntry 55 }

tBgpInstanceBfdStrictHoldTime    OBJECT-TYPE
    SYNTAX      Unsigned32 (1..65535)
    MAX-ACCESS  read-create
    STATUS      current
    DESCRIPTION
        "The value of tBgpInstanceBfdStrictHoldTime specifies the BGP session
         hold time when the strict mode BFD session is not successfully
         established.

         When the value is not '0' the BGP session will be bounced after the
         configured time"
    DEFVAL      { 30 }
    ::= { tBgpInstanceParamsExtEntry 56 }

tBgpInstanceAttrSetRemove        OBJECT-TYPE
    SYNTAX      TruthValue
    MAX-ACCESS  read-create
    STATUS      current
    DESCRIPTION
        "The value of tBgpInstanceAttrSetRemove controls reception of ATTR_SET
         in  routes received from VPRN BGP peers (PE-CE sessions).

         When it is set to 'true', it instructs BGP to remove ATTR_SET in
         received BGP routes  from PE-CE peers at a stage before the ATTR_SET
         could even be used for BGP best path  selection. The removal is done
         irrespective of whether the PE-CE routes are re-exported  as VPN-IP
         routes with new ATTR_SET attributes added.

         When it is set to 'false', it instructs BGP to leave ATTR_SET in
         received BGP routes  from PE-CE peers. The ATTR_SET is ignored and not
         used in BGP best path selection.  The ATTR_SET is copied into VPN-IP
         routes accepted by the VRF-export policy and advertised  to base
         router VPN-IP peers unless it is replaced by a new ATTR_SET as a
         result of  vRtrBgpIpVpnAttrSetExport is true."
    DEFVAL      { false }
    ::= { tBgpInstanceParamsExtEntry 62 }

tBgpInstLegacyFaultTolerance     OBJECT-TYPE
    SYNTAX      TruthValue
    MAX-ACCESS  read-create
    STATUS      current
    DESCRIPTION
        "The value of tBgpInstLegacyFaultTolerance specifies whether the legacy
         fault tolerance mode of BGP, and its related configuration, are
         permitted.

         When it is set to 'true', configuration for
         tBgpInstanceFaultTolerance, tBgpPGFaultTolerance  and
         tBgpPeerNgFaultTolerance is applied. Fault-tolerance is enabled or
         disabled as per these  set values.

         When it is set to 'false', configuration for
         tBgpInstanceFaultTolerance, tBgpPGFaultTolerance  and
         tBgpPeerNgFaultTolerance is ignored and fault-tolerance is always
         enabled.

         Fault-tolerance controls whether or not the non-disruptive approaches
         mentioned in RFC 7606 are used for handling a wide range of UPDATE
         message errors."
    DEFVAL      { false }
    ::= { tBgpInstanceParamsExtEntry 63 }

tBgpInstanceLLGRFamilyTblLstCh   OBJECT-TYPE
    SYNTAX      TimeStamp
    MAX-ACCESS  read-only
    STATUS      current
    DESCRIPTION
        "The value of tBgpInstanceLLGRFamilyTblLstCh indicates the timestamp
         when an entry in tBgpInstanceLLGRFamilyTable was last changed."
    ::= { tBgpInstanceObjects 25 }

tBgpInstanceLLGRFamilyTable      OBJECT-TYPE
    SYNTAX      SEQUENCE OF TBgpInstanceLLGRFamilyEntry
    MAX-ACCESS  not-accessible
    STATUS      current
    DESCRIPTION
        "The tBgpInstanceLLGRFamilyTable consists of information about the BGP
         LLGR Family specific parameters. The table entries are indexed by BGP
         instance and LLGR AFI/SAFI."
    ::= { tBgpInstanceObjects 26 }

tBgpInstanceLLGRFamilyEntry      OBJECT-TYPE
    SYNTAX      TBgpInstanceLLGRFamilyEntry
    MAX-ACCESS  not-accessible
    STATUS      current
    DESCRIPTION
        "An entry (conceptual row) in the tBgpInstanceLLGRFamilyTable."
    INDEX       {
        tBgpInstanceIndex,
        tBgpInstanceLLGRFamily
    }
    ::= { tBgpInstanceLLGRFamilyTable 1 }

TBgpInstanceLLGRFamilyEntry      ::= SEQUENCE
{
    tBgpInstanceLLGRFamily           TmnxIpFamilyIdentifier,
    tBgpInstanceLLGRFamilyLstCh      TimeStamp,
    tBgpInstanceLLGRFamilyRowStatus  RowStatus,
    tBgpInstLLGRFamilyAdvStaleTime   Unsigned32,
    tBgpInstLLGRFamilyOvrideStaleTm  Unsigned32
}

tBgpInstanceLLGRFamily           OBJECT-TYPE
    SYNTAX      TmnxIpFamilyIdentifier
    MAX-ACCESS  not-accessible
    STATUS      current
    DESCRIPTION
        "The value of tBgpInstanceLLGRFamily specifies the particular AFI/SAFI
         that this configuration applies to."
    ::= { tBgpInstanceLLGRFamilyEntry 1 }

tBgpInstanceLLGRFamilyLstCh      OBJECT-TYPE
    SYNTAX      TimeStamp
    MAX-ACCESS  read-only
    STATUS      current
    DESCRIPTION
        "The value tBgpInstanceLLGRFamilyLstCh indicates when an entry in
         tBgpInstanceLLGRFamilyTable was last changed."
    ::= { tBgpInstanceLLGRFamilyEntry 2 }

tBgpInstanceLLGRFamilyRowStatus  OBJECT-TYPE
    SYNTAX      RowStatus
    MAX-ACCESS  read-create
    STATUS      current
    DESCRIPTION
        "RowStatus for the LLGR Family entry."
    ::= { tBgpInstanceLLGRFamilyEntry 3 }

tBgpInstLLGRFamilyAdvStaleTime   OBJECT-TYPE
    SYNTAX      Unsigned32 (0..16777215)
    MAX-ACCESS  read-create
    STATUS      current
    DESCRIPTION
        "The value of tBgpInstLLGRFamilyAdvStaleTime specifies the time for
         which the route can be used for this AFI/SAFI after the peer is
         disconnected."
    DEFVAL      { 86400 }
    ::= { tBgpInstanceLLGRFamilyEntry 4 }

tBgpInstLLGRFamilyOvrideStaleTm  OBJECT-TYPE
    SYNTAX      Unsigned32 (0..16777216)
    MAX-ACCESS  read-create
    STATUS      current
    DESCRIPTION
        "The value of tBgpInstLLGRFamilyOvrideStaleTm specifies the stale time
         for this particular AFI/SAFI when the system is in helper mode."
    DEFVAL      { 16777216 }
    ::= { tBgpInstanceLLGRFamilyEntry 5 }

tBgpConvergenceTblLstCh          OBJECT-TYPE
    SYNTAX      TimeStamp
    MAX-ACCESS  read-only
    STATUS      current
    DESCRIPTION
        "The value of tBgpConvergenceTblLstCh indicates the last timestamp when
         an entry in the tBgpConvergenceTable was last changed."
    ::= { tBgpInstanceObjects 27 }

tBgpConvergenceTable             OBJECT-TYPE
    SYNTAX      SEQUENCE OF TBgpConvergenceEntry
    MAX-ACCESS  not-accessible
    STATUS      current
    DESCRIPTION
        "The tBgpConvergenceTable is the list of configured objects  for
         different family types to delay advertisement of BGP  routes until
         convergence has occurred.

         The table entries are indexed by BGP instance and family type."
    ::= { tBgpInstanceObjects 28 }

tBgpConvergenceEntry             OBJECT-TYPE
    SYNTAX      TBgpConvergenceEntry
    MAX-ACCESS  not-accessible
    STATUS      current
    DESCRIPTION
        "An entry (conceptual row) in the tBgpConvergenceTable.

         An entry is created when an entry in tBgpInstanceEntry is. When
         created, all objects are initialized to their default values."
    INDEX       {
        tBgpInstanceIndex,
        tBgpConvergenceFamily
    }
    ::= { tBgpConvergenceTable 1 }

TBgpConvergenceEntry             ::= SEQUENCE
{
    tBgpConvergenceFamily            TmnxIpFamilyIdentifier,
    tBgpConvergenceLstCh             TimeStamp,
    tBgpConvergenceMaxWaitToAdv      Unsigned32,
    tBgpConvTimerEstablishedPeers    Unsigned32,
    tBgpConvEstablishedPeers         Unsigned32,
    tBgpConvFirstSessEstablishedTime Unsigned32,
    tBgpConvLastSessEstablishedTime  Unsigned32,
    tBgpConvergedPeers               Unsigned32,
    tBgpConvergenceState             INTEGER,
    tBgpConvergenceTime              Unsigned32,
    tBgpConvergenceOperMaxWaitToAdv  Unsigned32
}

tBgpConvergenceFamily            OBJECT-TYPE
    SYNTAX      TmnxIpFamilyIdentifier
    MAX-ACCESS  read-only
    STATUS      current
    DESCRIPTION
        "The value of tBgpConvergenceFamily specifies the address family for
         which the convergence selection applies."
    ::= { tBgpConvergenceEntry 1 }

tBgpConvergenceLstCh             OBJECT-TYPE
    SYNTAX      TimeStamp
    MAX-ACCESS  read-only
    STATUS      current
    DESCRIPTION
        "The value tBgpConvergenceLstCh indicates when an entry in
         tBgpConvergenceTable was last changed."
    ::= { tBgpConvergenceEntry 2 }

tBgpConvergenceMaxWaitToAdv      OBJECT-TYPE
    SYNTAX      Unsigned32 (0..3600)
    UNITS       "seconds"
    MAX-ACCESS  read-create
    STATUS      current
    DESCRIPTION
        "The value of tBgpConvergenceMaxWaitToAdv specifies the maximum amount
         of time,  in seconds, measured from the time when the first session
         (configured  or dynamic) that supports the address family comes up
         after a BGP  restart, until BGP is allowed to advertise any routes in
         that address  family to any peer."
    DEFVAL      { 0 }
    ::= { tBgpConvergenceEntry 3 }

tBgpConvTimerEstablishedPeers    OBJECT-TYPE
    SYNTAX      Unsigned32
    MAX-ACCESS  read-only
    STATUS      current
    DESCRIPTION
        "The value of tBgpConvTimerEstablishedPeers indicates the number of BGP
         sessions (configured and dynamic) that support the address  family and
         that were in established state when tBgpInstanceConvMinWaitToAdv
         timer expired."
    ::= { tBgpConvergenceEntry 4 }

tBgpConvEstablishedPeers         OBJECT-TYPE
    SYNTAX      Unsigned32
    MAX-ACCESS  read-only
    STATUS      current
    DESCRIPTION
        "The value of tBgpConvEstablishedPeers that support the address  family
         and that currently in established state."
    ::= { tBgpConvergenceEntry 5 }

tBgpConvFirstSessEstablishedTime OBJECT-TYPE
    SYNTAX      Unsigned32
    MAX-ACCESS  read-only
    STATUS      current
    DESCRIPTION
        "The value of tBgpConvFirstSessEstablishedTime indicates the  first
         session supporting the address family came up, measured  from the time
         that BGP instance restarted."
    ::= { tBgpConvergenceEntry 6 }

tBgpConvLastSessEstablishedTime  OBJECT-TYPE
    SYNTAX      Unsigned32
    MAX-ACCESS  read-only
    STATUS      current
    DESCRIPTION
        "The value of tBgpConvLastSessEstablishedTime indicates  the last
         session supporting the address family came up,  measured from the time
         that the BGP instance restarted."
    ::= { tBgpConvergenceEntry 7 }

tBgpConvergedPeers               OBJECT-TYPE
    SYNTAX      Unsigned32
    MAX-ACCESS  read-only
    STATUS      current
    DESCRIPTION
        "The value of tBgpConvergedPeers indicates the number of peers that
         have  sent an EOR marker for the address family since the last BGP
         restart."
    ::= { tBgpConvergenceEntry 8 }

tBgpConvergenceState             OBJECT-TYPE
    SYNTAX      INTEGER {
        waiting   (1),
        started   (2),
        partial   (3),
        timeout   (4),
        converged (5)
    }
    MAX-ACCESS  read-only
    STATUS      current
    DESCRIPTION
        "The value of tBgpConvergenceState indicates the convergence state of
         the address family."
    ::= { tBgpConvergenceEntry 9 }

tBgpConvergenceTime              OBJECT-TYPE
    SYNTAX      Unsigned32
    MAX-ACCESS  read-only
    STATUS      current
    DESCRIPTION
        "The value of tBgpConvergenceTime indicates the elapsed time in
         seconds,  starting from the last BGP restart, to reach the converged
         state for the  address family."
    ::= { tBgpConvergenceEntry 10 }

tBgpConvergenceOperMaxWaitToAdv  OBJECT-TYPE
    SYNTAX      Unsigned32
    UNITS       "seconds"
    MAX-ACCESS  read-only
    STATUS      current
    DESCRIPTION
        "tBgpConvergenceOperMaxWaitToAdv indicates the operational timer value after which
         the local BGP instance starts advertising all its own family RIB-OUTs
         to all corresponding family established  peers."
    DEFVAL      { 0 }
    ::= { tBgpConvergenceEntry 11 }

tBgpInstMultipathNgTable         OBJECT-TYPE
    SYNTAX      SEQUENCE OF TBgpInstMultipathNgEntry
    MAX-ACCESS  not-accessible
    STATUS      current
    DESCRIPTION
        "The tBgpInstMultipathNgTable is the list of configured multi-path
         mechanisms for different BGP family types.

         The table entries are indexed by BGP instance and family type. Each
         entry denotes the multi-path selection used to select the number of
         paths of a specific BGP family type."
    ::= { tBgpInstanceObjects 29 }

tBgpInstMultipathNgEntry         OBJECT-TYPE
    SYNTAX      TBgpInstMultipathNgEntry
    MAX-ACCESS  not-accessible
    STATUS      current
    DESCRIPTION
        "An entry (conceptual row) in the tBgpInstMultipathNgTable.

         When created, all objects are initialized to their default values."
    INDEX       {
        tBgpInstanceIndex,
        tBgpInstMultipathNgFamily
    }
    ::= { tBgpInstMultipathNgTable 1 }

TBgpInstMultipathNgEntry         ::= SEQUENCE
{
    tBgpInstMultipathNgFamily        TmnxIpFamilyIdentifier,
    tBgpInstMultipathNgRowStatus     RowStatus,
    tBgpInstMultipathNgLstCh         TimeStamp,
    tBgpInstMultipathNgBgp           Integer32,
    tBgpInstMultipathNgEBgp          Integer32,
    tBgpInstMultipathNgIBgp          Integer32,
    tBgpInstMultipathNgRestrict      INTEGER,
    tBgpInstMultipathNgUnequalCost   TruthValue
}

tBgpInstMultipathNgFamily        OBJECT-TYPE
    SYNTAX      TmnxIpFamilyIdentifier
    MAX-ACCESS  not-accessible
    STATUS      current
    DESCRIPTION
        "The value of tBgpInstMultipathNgFamily specifies the address family
         for which the multi-path selection applies."
    ::= { tBgpInstMultipathNgEntry 1 }

tBgpInstMultipathNgRowStatus     OBJECT-TYPE
    SYNTAX      RowStatus
    MAX-ACCESS  read-create
    STATUS      current
    DESCRIPTION
        "The value of tBgpInstMultipathNgRowStatus specifies the row status for
         this table entry. It is used to create and delete row entries in this
         table."
    ::= { tBgpInstMultipathNgEntry 2 }

tBgpInstMultipathNgLstCh         OBJECT-TYPE
    SYNTAX      TimeStamp
    MAX-ACCESS  read-only
    STATUS      current
    DESCRIPTION
        "The value tBgpInstMultipathNgLstCh indicates when an entry in
         tBgpInstMultipathNgTable was last changed."
    ::= { tBgpInstMultipathNgEntry 3 }

tBgpInstMultipathNgBgp           OBJECT-TYPE
    SYNTAX      Integer32 (0..64)
    UNITS       "number-of-paths"
    MAX-ACCESS  read-create
    STATUS      current
    DESCRIPTION
        "The value of tBgpInstMultipathNgBgp specifies if BGP multipath is
         enabled or disabled for this instance and family.

         A value of '0' would disable address family specific BGP multipath.

         Any other value would specify the number of paths for BGP Multipath."
    DEFVAL      { 0 }
    ::= { tBgpInstMultipathNgEntry 4 }

tBgpInstMultipathNgEBgp          OBJECT-TYPE
    SYNTAX      Integer32 (0..64)
    UNITS       "number-of-paths"
    MAX-ACCESS  read-create
    STATUS      current
    DESCRIPTION
        "The value of tBgpInstMultipathNgEBgp specifies the maximum number of
         paths that can be installed into RTM when the best path is received
         from an EBGP peer.

         A value of '0' would indicate to use the number of paths from
         tBgpInstMultipathNgBgp.

         Any other value would specify the number of paths for EBGP Multipath."
    DEFVAL      { 0 }
    ::= { tBgpInstMultipathNgEntry 5 }

tBgpInstMultipathNgIBgp          OBJECT-TYPE
    SYNTAX      Integer32 (0..64)
    UNITS       "number-of-paths"
    MAX-ACCESS  read-create
    STATUS      current
    DESCRIPTION
        "The value of tBgpInstMultipathNgIBgp specifies the maximum number of
         paths that can be installed into RTM when the best path is received
         from an IBGP peer.

         A value of '0' would indicate to use the number of paths from
         tBgpInstMultipathNgBgp.

         Any other value would specify the number of paths for IBGP Multipath."
    DEFVAL      { 0 }
    ::= { tBgpInstMultipathNgEntry 6 }

tBgpInstMultipathNgRestrict      OBJECT-TYPE
    SYNTAX      INTEGER {
        sameAsPathLength (1),
        sameNeighborAs   (2),
        exactAsPath      (3)
    }
    MAX-ACCESS  read-create
    STATUS      current
    DESCRIPTION
        "When the value of tBgpInstMultipathNgRestrict is set to
         'sameAsPathLength', it forces multipaths to have the same AS path
          length (unless as-path-ignore is configured).

         When the value of tBgpInstMultipathNgRestrict is set to
         'sameNeighborAs', it forces multipaths to have the same AS path length
         (unless as-path-ignore is configured) and the same neighbor AS.

         When the value of tBgpInstMultipathNgRestrict is set to 'exactAsPath'
         it forces multipaths to have the exact same AS paths, meaning the same
         ASNs in exactly the same order and contained in exactly the same types
         of elements."
    DEFVAL      { sameAsPathLength }
    ::= { tBgpInstMultipathNgEntry 7 }

tBgpInstMultipathNgUnequalCost   OBJECT-TYPE
    SYNTAX      TruthValue
    MAX-ACCESS  read-create
    STATUS      current
    DESCRIPTION
        "The value of tBgpInstMultipathNgUnequalCost specifies the selection of
         multipaths ignores differences in next-hop cost compared to the best
         path."
    DEFVAL      { false }
    ::= { tBgpInstMultipathNgEntry 8 }

tBgpLUStatsTblLstCh              OBJECT-TYPE
    SYNTAX      TimeStamp
    MAX-ACCESS  read-only
    STATUS      current
    DESCRIPTION
        "The value of tBgpLUStatsTblLstCh indicates the last timestamp when an
         entry in the tBgpLUStatsTable was last changed."
    ::= { tBgpInstanceObjects 30 }

tBgpLUStatsTable                 OBJECT-TYPE
    SYNTAX      SEQUENCE OF TBgpLUStatsEntry
    MAX-ACCESS  not-accessible
    STATUS      current
    DESCRIPTION
        "The tBgpLUStatsTable is traffic stats for BGP-LU tunnels on egress and
         ingress data path.

         The table entries are indexed by BGP instance family type  and prefix."
    ::= { tBgpInstanceObjects 31 }

tBgpLUStatsEntry                 OBJECT-TYPE
    SYNTAX      TBgpLUStatsEntry
    MAX-ACCESS  not-accessible
    STATUS      current
    DESCRIPTION
        "An entry (conceptual row) in the tBgpLUStatsTable.

         An entry is created when an entry in tBgpInstanceEntry is. When
         created, all objects are initialized to their default values."
    INDEX       {
        tBgpInstanceIndex,
        tBgpLUStatsFamily,
        tBgpLUStatsPrefixType,
        tBgpLUStatsPrefix,
        tBgpLUStatsPrefixLength
    }
    ::= { tBgpLUStatsTable 1 }

TBgpLUStatsEntry                 ::= SEQUENCE
{
    tBgpLUStatsFamily                TmnxIpFamilyIdentifier,
    tBgpLUStatsPrefixType            InetAddressType,
    tBgpLUStatsPrefix                InetAddress,
    tBgpLUStatsPrefixLength          InetAddressPrefixLength,
    tBgpLUStatsLstCh                 TimeStamp,
    tBgpLUStatsNextHopType           InetAddressType,
    tBgpLUStatsNextHopAddress        InetAddress,
    tBgpLUStatsIngressOperState      TmnxOperState,
    tBgpLUStatsIngressLabel          Unsigned32,
    tBgpLUIngressStatsPktCnt         Counter64,
    tBgpLUIngressStatsOctetsCnt      Counter64,
    tBgpLUStatsEgressOperState       TmnxOperState,
    tBgpLUStatsEgressLabel           Unsigned32,
    tBgpLUEgressStatsPktCnt          Counter64,
    tBgpLUEgressStatsOctetsCnt       Counter64
}

tBgpLUStatsFamily                OBJECT-TYPE
    SYNTAX      TmnxIpFamilyIdentifier
    MAX-ACCESS  read-only
    STATUS      current
    DESCRIPTION
        "The value of tBgpLUStatsFamily specifies the address family for which
         the BGP-LU stats applies."
    ::= { tBgpLUStatsEntry 1 }

tBgpLUStatsPrefixType            OBJECT-TYPE
    SYNTAX      InetAddressType
    MAX-ACCESS  read-only
    STATUS      current
    DESCRIPTION
        "The value of tBgpLUStatsPrefixType specifies the address type of
         tBgpLUStatsPrefix prefix."
    ::= { tBgpLUStatsEntry 2 }

tBgpLUStatsPrefix                OBJECT-TYPE
    SYNTAX      InetAddress (SIZE (4|16|20))
    MAX-ACCESS  read-only
    STATUS      current
    DESCRIPTION
        "The value of tBgpLUStatsPrefix specifies the prefix for LU Stats
         Table."
    ::= { tBgpLUStatsEntry 3 }

tBgpLUStatsPrefixLength          OBJECT-TYPE
    SYNTAX      InetAddressPrefixLength (0..128)
    MAX-ACCESS  read-only
    STATUS      current
    DESCRIPTION
        "The value of tBgpLUStatsPrefixLength specifies the value of the prefix
         length for tBgpLUStatsPrefix"
    ::= { tBgpLUStatsEntry 4 }

tBgpLUStatsLstCh                 OBJECT-TYPE
    SYNTAX      TimeStamp
    MAX-ACCESS  read-only
    STATUS      current
    DESCRIPTION
        "The value tBgpLUStatsLstCh indicates when an entry in tBgpLUStatsTable
         was last changed."
    ::= { tBgpLUStatsEntry 5 }

tBgpLUStatsNextHopType           OBJECT-TYPE
    SYNTAX      InetAddressType
    MAX-ACCESS  read-only
    STATUS      current
    DESCRIPTION
        "The value of tBgpLUStatsNextHopType indicates the  address type of the
         nexthop."
    ::= { tBgpLUStatsEntry 6 }

tBgpLUStatsNextHopAddress        OBJECT-TYPE
    SYNTAX      InetAddress (SIZE (0|4|16))
    MAX-ACCESS  read-only
    STATUS      current
    DESCRIPTION
        "The value of tBgpLUStatsNextHopAddress indicates the address of the
         nexthop."
    ::= { tBgpLUStatsEntry 7 }

tBgpLUStatsIngressOperState      OBJECT-TYPE
    SYNTAX      TmnxOperState
    MAX-ACCESS  read-only
    STATUS      current
    DESCRIPTION
        "The value of tBgpLUStatsIngressOperState indicates the operational
         state."
    ::= { tBgpLUStatsEntry 8 }

tBgpLUStatsIngressLabel          OBJECT-TYPE
    SYNTAX      Unsigned32
    MAX-ACCESS  read-only
    STATUS      current
    DESCRIPTION
        "The value of tBgpLUStatsIngressLabel indicates the label on ingress."
    ::= { tBgpLUStatsEntry 9 }

tBgpLUIngressStatsPktCnt         OBJECT-TYPE
    SYNTAX      Counter64
    MAX-ACCESS  read-only
    STATUS      current
    DESCRIPTION
        "The value of tBgpLUIngressStatsPktCnt indicates the number of packets
         on ingress."
    ::= { tBgpLUStatsEntry 10 }

tBgpLUIngressStatsOctetsCnt      OBJECT-TYPE
    SYNTAX      Counter64
    MAX-ACCESS  read-only
    STATUS      current
    DESCRIPTION
        "The value of tBgpLUIngressStatsOctetsCnt indicates the number of
         octets on ingress."
    ::= { tBgpLUStatsEntry 11 }

tBgpLUStatsEgressOperState       OBJECT-TYPE
    SYNTAX      TmnxOperState
    MAX-ACCESS  read-only
    STATUS      current
    DESCRIPTION
        "The value of tBgpLUStatsEgressOperState indicates the operational
         state."
    ::= { tBgpLUStatsEntry 12 }

tBgpLUStatsEgressLabel           OBJECT-TYPE
    SYNTAX      Unsigned32
    MAX-ACCESS  read-only
    STATUS      current
    DESCRIPTION
        "The value of tBgpLUStatsEgressLabel indicates the label on egress."
    ::= { tBgpLUStatsEntry 13 }

tBgpLUEgressStatsPktCnt          OBJECT-TYPE
    SYNTAX      Counter64
    MAX-ACCESS  read-only
    STATUS      current
    DESCRIPTION
        "The value of tBgpLUEgressStatsPktCnt indicates the number of packets
         on egress."
    ::= { tBgpLUStatsEntry 14 }

tBgpLUEgressStatsOctetsCnt       OBJECT-TYPE
    SYNTAX      Counter64
    MAX-ACCESS  read-only
    STATUS      current
    DESCRIPTION
        "The value of tBgpLUEgressStatsOctetsCnt indicates the number of octets
         on egress."
    ::= { tBgpLUStatsEntry 15 }

tBgpSrv6TblLstCh                 OBJECT-TYPE
    SYNTAX      TimeStamp
    MAX-ACCESS  read-only
    STATUS      current
    DESCRIPTION
        "The value of tBgpSrv6TblLstCh indicates the last timestamp when an
         entry in the tBgpSrv6Table was last changed."
    ::= { tBgpInstanceObjects 32 }

tBgpSrv6Table                    OBJECT-TYPE
    SYNTAX      SEQUENCE OF TBgpSrv6Entry
    MAX-ACCESS  not-accessible
    STATUS      current
    DESCRIPTION
        "The tBgpSrv6Table is the list of configured objects  for different
         family types of segment-routing-v6.

         The table entries are indexed by BGP instance and family type."
    ::= { tBgpInstanceObjects 33 }

tBgpSrv6Entry                    OBJECT-TYPE
    SYNTAX      TBgpSrv6Entry
    MAX-ACCESS  not-accessible
    STATUS      current
    DESCRIPTION
        "An entry (conceptual row) in the tBgpSrv6Table. When created, all
         objects are initialized to their default values."
    INDEX       {
        tBgpInstanceIndex,
        tBgpSrv6Family
    }
    ::= { tBgpSrv6Table 1 }

TBgpSrv6Entry                    ::= SEQUENCE
{
    tBgpSrv6Family                   TmnxIpFamilyIdentifier,
    tBgpSrv6RowStatus                RowStatus,
    tBgpSrv6LstCh                    TimeStamp,
    tBgpSrv6AddTlv                   TruthValue,
    tBgpSrv6LocatorName              TLNamedItemOrEmpty,
    tBgpSrv6IgRecvTlv                TruthValue,
    tBgpSrv6Resolution               TSrv6RouteResolution,
    tBgpSrv6MSLocatorName            TLNamedItemOrEmpty,
    tBgpSrv6UpaTriggerNextHop        TBgpSrv6UpaTriggerNextHop
}

tBgpSrv6Family                   OBJECT-TYPE
    SYNTAX      TmnxIpFamilyIdentifier
    MAX-ACCESS  not-accessible
    STATUS      current
    DESCRIPTION
        "The value of tBgpSrv6Family specifies the address family for which the
         srv6 selection applies."
    ::= { tBgpSrv6Entry 1 }

tBgpSrv6RowStatus                OBJECT-TYPE
    SYNTAX      RowStatus
    MAX-ACCESS  read-create
    STATUS      current
    DESCRIPTION
        "The value of tBgpSrv6RowStatus specifies the row status for this table
         entry. It is used to create and delete row entries in this table."
    ::= { tBgpSrv6Entry 2 }

tBgpSrv6LstCh                    OBJECT-TYPE
    SYNTAX      TimeStamp
    MAX-ACCESS  read-only
    STATUS      current
    DESCRIPTION
        "The value tBgpSrv6LstCh indicates when an entry in tBgpSrv6Table was
         last changed."
    ::= { tBgpSrv6Entry 3 }

tBgpSrv6AddTlv                   OBJECT-TYPE
    SYNTAX      TruthValue
    MAX-ACCESS  read-create
    STATUS      current
    DESCRIPTION
        "The value of tBgpSrv6AddTlv specifies the Srv6 TLVs need to be added
         to outbound routes."
    DEFVAL      { false }
    ::= { tBgpSrv6Entry 4 }

tBgpSrv6LocatorName              OBJECT-TYPE
    SYNTAX      TLNamedItemOrEmpty
    MAX-ACCESS  read-create
    STATUS      current
    DESCRIPTION
        "The tBgpSrv6LocatorName specifies the SRv6 locator name used with this
         family."
    DEFVAL      { ''H }
    ::= { tBgpSrv6Entry 5 }

tBgpSrv6IgRecvTlv                OBJECT-TYPE
    SYNTAX      TruthValue
    MAX-ACCESS  read-create
    STATUS      current
    DESCRIPTION
        "The value of tBgpSrv6IgRecvTlv specifies the Srv6 TLVs need to be
         ignored  for received routes."
    DEFVAL      { true }
    ::= { tBgpSrv6Entry 6 }

tBgpSrv6Resolution               OBJECT-TYPE
    SYNTAX      TSrv6RouteResolution
    MAX-ACCESS  read-create
    STATUS      current
    DESCRIPTION
        "The value of tBgpSrv6Resolution specifies the resolution options for
         routes of this family."
    DEFVAL      { routeTable }
    ::= { tBgpSrv6Entry 7 }

tBgpSrv6MSLocatorName            OBJECT-TYPE
    SYNTAX      TLNamedItemOrEmpty
    MAX-ACCESS  read-create
    STATUS      current
    DESCRIPTION
        "The value of tBgpSrv6MSLocatorName specifies the SRv6 micro segment
         locator name used with this family."
    DEFVAL      { ''H }
    ::= { tBgpSrv6Entry 8 }

tBgpSrv6UpaTriggerNextHop        OBJECT-TYPE
    SYNTAX      TBgpSrv6UpaTriggerNextHop
    MAX-ACCESS  read-create
    STATUS      current
    DESCRIPTION
        "The value of tBgpSrv6UpaTriggerNextHop specifies the handling of UPA
         trigger for next-hop.

         none - BGP won't check the Unreachable Prefix Table to verify that
         there is no matching UPA entry.

         frr  - activate BGP to check the Unreachable Prefix Table to verify
         that there is no matching UPA entry (Longest Prefix Match).  Next-Hop
         of all BGP AFI/SAFI can use Unreachable Prefix Table fast detecting
         next-hop unreachability."
    DEFVAL      { none }
    ::= { tBgpSrv6Entry 9 }

tBgpUseLeakedRoutesTblLstCh      OBJECT-TYPE
    SYNTAX      TimeStamp
    MAX-ACCESS  read-only
    STATUS      current
    DESCRIPTION
        "The value of tBgpUseLeakedRoutesTblLstCh indicates the timestamp when
         an entry in the tBgpUseLeakedRoutesTable was last changed."
    ::= { tBgpInstanceObjects 34 }

tBgpUseLeakedRoutesTable         OBJECT-TYPE
    SYNTAX      SEQUENCE OF TBgpUseLeakedRoutesEntry
    MAX-ACCESS  not-accessible
    STATUS      current
    DESCRIPTION
        "The tBgpUseLeakedRoutesTable consists of information about the BGP Use
         Leaked Routes parameters.

         The table entries are indexed by BGP instance."
    ::= { tBgpInstanceObjects 35 }

tBgpUseLeakedRoutesEntry         OBJECT-TYPE
    SYNTAX      TBgpUseLeakedRoutesEntry
    MAX-ACCESS  not-accessible
    STATUS      current
    DESCRIPTION
        "An entry (conceptual row) in the tBgpUseLeakedRoutesTable.

         An entry is created when an entry in tBgpInstanceEntry is."
    AUGMENTS    { tBgpInstanceEntry }
    ::= { tBgpUseLeakedRoutesTable 1 }

TBgpUseLeakedRoutesEntry         ::= SEQUENCE
{ tBgpUseLeakedRoutesStatic        TruthValue }

tBgpUseLeakedRoutesStatic        OBJECT-TYPE
    SYNTAX      TruthValue
    MAX-ACCESS  read-create
    STATUS      current
    DESCRIPTION
        "The value of tBgpUseLeakedRoutesStatic specifies whether non-leaked
         IPv4-unicast or IPv6-unicast route will be resolved by leaked static
         routes

         When the value is 'true', non-leaked IPv4-unicast or IPv6-unicast
         route should  be resolved by leaked static routes.

         When the value is 'false', non-leaked IPv4-unicast or IPv6-unicast
         route should not be resolved by leaked static routes."
    DEFVAL      { false }
    ::= { tBgpUseLeakedRoutesEntry 1 }

tBgpPeerGroupObjects             OBJECT IDENTIFIER ::= { tBgpObjects 3 }

tBgpPeerGroupTableLastChanged    OBJECT-TYPE
    SYNTAX      TimeStamp
    MAX-ACCESS  read-only
    STATUS      current
    DESCRIPTION
        "The value of tBgpPeerGroupTableLastChanged indicates the last
         timestamp when an entry in the tBgpPeerGroupTable was last changed."
    ::= { tBgpPeerGroupObjects 1 }

tBgpPeerGroupTableSpinlock       OBJECT-TYPE
    SYNTAX      TestAndIncr
    MAX-ACCESS  read-write
    STATUS      current
    DESCRIPTION
        "The value of tBgpPeerGroupTableSpinlock specifies voluntary
         serialization control for tBgpPeerGroupTable. It is mainly used to
         coordinate changes to tBgpPeerGroupInheritance."
    DEFVAL      { 0 }
    ::= { tBgpPeerGroupObjects 2 }

tBgpPeerGroupTable               OBJECT-TYPE
    SYNTAX      SEQUENCE OF TBgpPeerGroupEntry
    MAX-ACCESS  not-accessible
    STATUS      current
    DESCRIPTION
        "The tBgpPeerGroupTable is the list of configured BGP Peer Groups. The
         table entries are indexed by the Peer Group Name."
    ::= { tBgpPeerGroupObjects 3 }

tBgpPeerGroupEntry               OBJECT-TYPE
    SYNTAX      TBgpPeerGroupEntry
    MAX-ACCESS  not-accessible
    STATUS      current
    DESCRIPTION
        "An entry (conceptual row) in the tBgpPeerGroupTable.

         An entry can be created using the row status object,
         tBgpPeerGroupRowStatus. When created, all objects are initialized to
         their default values.

         Before the Peer entry can be used, tBgpPeerGroupRowStatus must be set
         to 'active(1)'. The Peer entry can be removed by setting
         tBgpPeerRowStatus to 'destroy(6)'."
    INDEX       {
        tBgpInstanceIndex,
        tBgpPeerGroupName
    }
    ::= { tBgpPeerGroupTable 1 }

TBgpPeerGroupEntry               ::= SEQUENCE
{
    tBgpPeerGroupName                BgpPeerGroupName,
    tBgpPeerGroupRowStatus           RowStatus,
    tBgpPeerGroupShutdown            TmnxAdminStateTruthValue,
    tBgpPeerGroupDescription         DisplayString,
    tBgpPeerGroupConnectRetry        BgpConnectRetryTime,
    tBgpPeerGroupHoldTime            BgpHoldTime,
    tBgpPeerGroupKeepAlive           BgpKeepAliveTime,
    tBgpPeerGroupMinASOrigination    BgpMinASOriginationTime,
    tBgpPeerGroupDampening           TruthValue,
    tBgpPeerGroupLocalAddress        IpAddress,
    tBgpPeerGroupLocalAS             TmnxBgpAutonomousSystem,
    tBgpPeerGroupLocalPreference     TmnxBgpLocalPreference,
    tBgpPeerGroupLoopDetect          BgpLoopDetect,
    tBgpPeerGroupMinRouteAdvertisement BgpMinRouteAdvertisement,
    tBgpPeerGroupMaxPrefix           BgpPrefixLimit,
    tBgpPeerGroupMEDSource           BgpMEDSource,
    tBgpPeerGroupMEDValue            BgpMEDValue,
    tBgpPeerGroupMultihop            BgpTimeToLive,
    tBgpPeerGroupNextHopSelf         TruthValue,
    tBgpPeerGroupNoAggregatorID      TruthValue,
    tBgpPeerGroupPassive             TruthValue,
    tBgpPeerGroupPeerAS              TmnxBgpAutonomousSystem,
    tBgpPeerGroupPeerType            BgpPeerType,
    tBgpPeerGroupPreference          TmnxBgpPreference,
    tBgpPeerGroupRemovePrivateAS     TruthValue,
    tBgpPeerGroupLastChanged         TimeStamp,
    tBgpPeerGroupInheritance         Counter64,
    tBgpPeerGroupImportPolicy1       TPolicyStatementNameOrEmpty,
    tBgpPeerGroupImportPolicy2       TPolicyStatementNameOrEmpty,
    tBgpPeerGroupImportPolicy3       TPolicyStatementNameOrEmpty,
    tBgpPeerGroupImportPolicy4       TPolicyStatementNameOrEmpty,
    tBgpPeerGroupImportPolicy5       TPolicyStatementNameOrEmpty,
    tBgpPeerGroupExportPolicy1       TPolicyStatementNameOrEmpty,
    tBgpPeerGroupExportPolicy2       TPolicyStatementNameOrEmpty,
    tBgpPeerGroupExportPolicy3       TPolicyStatementNameOrEmpty,
    tBgpPeerGroupExportPolicy4       TPolicyStatementNameOrEmpty,
    tBgpPeerGroupExportPolicy5       TPolicyStatementNameOrEmpty,
    tBgpPeerGroupOperStatus          BgpOperState,
    tBgpPeerGroupLocalASPrivate      TruthValue,
    tBgpPeerGroupMd5Auth             TruthValue,
    tBgpPeerGroupMd5AuthKey          DisplayString,
    tBgpPeerGroupClusterId           IpAddress,
    tBgpPeerGroupDisableClientReflect TruthValue,
    tBgpPeerGroupGracefulRestart     TruthValue,
    tBgpPeerGroupGRRestartTime       Unsigned32,
    tBgpPeerGroupGRStaleRoute        Unsigned32,
    tBgpPeerGroupGRAdminState        TmnxAdminState,
    tBgpPeerGroupGROperState         TmnxOperState,
    tBgpPeerGroupFamily              TmnxIpFamily,
    tBgpPeerGroupVpnApplyImport      TruthValue,
    tBgpPeerGroupVpnApplyExport      TruthValue,
    tBgpPeerGroupASOverride          TruthValue,
    tBgpPeerGroupOrf                 TruthValue,
    tBgpPeerGroupExtCommsOrf         TruthValue,
    tBgpPeerGroupExtCommsSendOrf     TruthValue,
    tBgpPeerGroupExtCommsRecvOrf     TruthValue,
    tBgpPeerGroupDynamicPeerGroup    TruthValue,
    tBgpPeerGroupLocalAS4Byte        InetAutonomousSystemNumber,
    tBgpPeerGroupPeerAS4Byte         InetAutonomousSystemNumber,
    tBgpPeerGroupDisable4ByteASN     TruthValue,
    tBgpPeerGroupHoldTimeIsStrict    TruthValue,
    tBgpPeerGroupRemovePrivateASLmtd TruthValue,
    tBgpPeerGroupPMTUDiscovery       TruthValue,
    tBgpPeerGroupMaxPrefixLogOnly    TruthValue,
    tBgpPeerGroupMaxPrefixThreshold  Unsigned32,
    tBgpPeerGroupDisableCapNego      TruthValue,
    tBgpPeerGroupCreationOrigin      TmnxCreateOrigin
}

tBgpPeerGroupName                OBJECT-TYPE
    SYNTAX      BgpPeerGroupName
    MAX-ACCESS  read-create
    STATUS      current
    DESCRIPTION
        "The value of tBgpPeerGroupName specifies the name of the Peer Group
         for the entry."
    ::= { tBgpPeerGroupEntry 1 }

tBgpPeerGroupRowStatus           OBJECT-TYPE
    SYNTAX      RowStatus
    MAX-ACCESS  read-create
    STATUS      current
    DESCRIPTION
        "The value of tBgpPeerGroupRowStatus specifies the row status for this
         BGP instance for the virtual router. It is used to create and delete
         row entries in this table.

         In order for an attempt to 'destroy' this row entry to succeed, the
         value of tBgpPeerGroupShutdown must be 'true'."
    ::= { tBgpPeerGroupEntry 2 }

tBgpPeerGroupShutdown            OBJECT-TYPE
    SYNTAX      TmnxAdminStateTruthValue
    MAX-ACCESS  read-create
    STATUS      current
    DESCRIPTION
        "The value of tBgpPeerGroupShutdown controls whether or not to
         advertise peers in this group or not.

         A value of 'false(2)' means no shutdown, so advertise peers under this
         group.

         A value of 'true(1)' means this entry is shutdown, so do not advertise
         peers in this group."
    DEFVAL      { false }
    ::= { tBgpPeerGroupEntry 3 }

tBgpPeerGroupDescription         OBJECT-TYPE
    SYNTAX      DisplayString (SIZE (0..80))
    MAX-ACCESS  read-create
    STATUS      current
    DESCRIPTION
        "The value of tBgpPeerGroupDescription specifies a user provided
         description string for this Peer Group. It can consist of any
         printable, seven-bit ASCII characters up to 80 characters in length."
    DEFVAL      { ''H }
    ::= { tBgpPeerGroupEntry 4 }

tBgpPeerGroupConnectRetry        OBJECT-TYPE
    SYNTAX      BgpConnectRetryTime
    UNITS       "seconds"
    MAX-ACCESS  read-create
    STATUS      current
    DESCRIPTION
        "The value of tBgpPeerGroupConnectRetry specifies the value (in
         seconds) of the BGP Connect Retry timer."
    REFERENCE
        "BGP4-MIB.bgpPeerConnectRetryInterval"
    DEFVAL      { 120 }
    ::= { tBgpPeerGroupEntry 5 }

tBgpPeerGroupHoldTime            OBJECT-TYPE
    SYNTAX      BgpHoldTime
    UNITS       "seconds"
    MAX-ACCESS  read-create
    STATUS      current
    DESCRIPTION
        "The value of tBgpPeerGroupHoldTime specifies the value (in seconds) of
         the BGP Hold Time."
    REFERENCE
        "BGP4-MIB.bgpPeerHoldTime"
    DEFVAL      { 90 }
    ::= { tBgpPeerGroupEntry 6 }

tBgpPeerGroupKeepAlive           OBJECT-TYPE
    SYNTAX      BgpKeepAliveTime
    UNITS       "seconds"
    MAX-ACCESS  read-create
    STATUS      current
    DESCRIPTION
        "The value of tBgpPeerGroupKeepAlive specifies the value of the BGP
         Keepalive timer.

         A keepalive message is sent every time this timer expires."
    REFERENCE
        "BGP4-MIB.bgpPeerKeepAlive"
    DEFVAL      { 30 }
    ::= { tBgpPeerGroupEntry 7 }

tBgpPeerGroupMinASOrigination    OBJECT-TYPE
    SYNTAX      BgpMinASOriginationTime
    UNITS       "seconds"
    MAX-ACCESS  read-create
    STATUS      obsolete
    DESCRIPTION
        "The value of tBgpPeerGroupMinASOrigination specifies the minimal
         interval (in seconds) at which a given path attribute can be
         advertised to a peer.

         This object was obsoleted in release 12.0."
    REFERENCE
        "BGP4-MIB.bgpPeerMinASOriginationInterval"
    DEFVAL      { 15 }
    ::= { tBgpPeerGroupEntry 8 }

tBgpPeerGroupDampening           OBJECT-TYPE
    SYNTAX      TruthValue
    MAX-ACCESS  read-create
    STATUS      current
    DESCRIPTION
        "The value of tBgpPeerGroupDampening specifies if route dampening is
         applied to learned routes."
    DEFVAL      { false }
    ::= { tBgpPeerGroupEntry 9 }

tBgpPeerGroupLocalAddress        OBJECT-TYPE
    SYNTAX      IpAddress
    MAX-ACCESS  read-create
    STATUS      obsolete
    DESCRIPTION
        "The value of tBgpPeerGroupLocalAddress specifies the local IP address
         to be used by peers in this group if not configured for the peer as
         advertisement source address.

         If set to 0.0.0.0, then use a (non-0.0.0.0) Peer Group Local Address,
         or a (non-0.0.0.0) global Local Address. If both are zero then find
         the local address by querying the closest interface to the peer
         address from the routing table."
    DEFVAL      { '00000000'H }
    ::= { tBgpPeerGroupEntry 10 }

tBgpPeerGroupLocalAS             OBJECT-TYPE
    SYNTAX      TmnxBgpAutonomousSystem
    MAX-ACCESS  read-create
    STATUS      obsolete
    DESCRIPTION
        "The value of tBgpPeerGroupLocalAS specifies the autonomous system
         number to be advertised for peers under this group.

         This object was obsoleted in release 7.0.  It is replaced with the
         4-byte AS number defined by tBgpPeerGroupLocalAS4Byte."
    DEFVAL      { 0 }
    ::= { tBgpPeerGroupEntry 11 }

tBgpPeerGroupLocalPreference     OBJECT-TYPE
    SYNTAX      TmnxBgpLocalPreference
    MAX-ACCESS  read-create
    STATUS      current
    DESCRIPTION
        "The value of tBgpPeerGroupLocalPreference specifies the default value
         for the Local Preference attribute. This value is used if the BGP
         route arrives from a BGP peer without the Local Preference attribute
         set.

         It is overridden by any value set via a route policy."
    DEFVAL      { 100 }
    ::= { tBgpPeerGroupEntry 12 }

tBgpPeerGroupLoopDetect          OBJECT-TYPE
    SYNTAX      BgpLoopDetect
    MAX-ACCESS  read-create
    STATUS      current
    DESCRIPTION
        "The value of tBgpPeerGroupLoopDetect determines how the peer session
         should deal with loop detection in the AS Path."
    DEFVAL      { ignore }
    ::= { tBgpPeerGroupEntry 13 }

tBgpPeerGroupMinRouteAdvertisement OBJECT-TYPE
    SYNTAX      BgpMinRouteAdvertisement
    UNITS       "seconds"
    MAX-ACCESS  read-create
    STATUS      current
    DESCRIPTION
        "The value of tBgpPeerGroupMinRouteAdvertisement specifies the minimum
         interval at which a given path attribute is advertised to a peer."
    DEFVAL      { 30 }
    ::= { tBgpPeerGroupEntry 14 }

tBgpPeerGroupMaxPrefix           OBJECT-TYPE
    SYNTAX      BgpPrefixLimit
    UNITS       "number of routes"
    MAX-ACCESS  read-create
    STATUS      obsolete
    DESCRIPTION
        "The value of tBgpPeerGroupMaxPrefix specifies the maximum number of
         routes that can be learned from this peer.

         A value of zero specifies there is no limit to the number of routes
         learned.

         The tBgpMaxNgPrefixThreshReached notification is sent when the number
         of routes exceeds a percentage of this limit as specified by
         tBgpPeerGroupMaxPrefixThreshold.

         When the number of routes exceeds this limit, then BGP peering will be
         disabled and the tBgpMaxNgPrefix100 notification will be sent.

         This object was obsoleted in release 13.0."
    DEFVAL      { 0 }
    ::= { tBgpPeerGroupEntry 15 }

tBgpPeerGroupMEDSource           OBJECT-TYPE
    SYNTAX      BgpMEDSource
    MAX-ACCESS  read-create
    STATUS      current
    DESCRIPTION
        "The value of tBgpPeerGroupMEDSource specifies the source of the Multi
         Exit Discriminator (MED) value for peers in this group."
    DEFVAL      { noMedOut }
    ::= { tBgpPeerGroupEntry 16 }

tBgpPeerGroupMEDValue            OBJECT-TYPE
    SYNTAX      BgpMEDValue
    MAX-ACCESS  read-create
    STATUS      current
    DESCRIPTION
        "The value of tBgpPeerGroupMEDValue specifies the value of MED when
         tBgpPeerGroupMEDSource is 'metricVal'. If the value of
         tBgpPeerGroupMEDSource is not 'metricVal', this object is ignored."
    DEFVAL      { 0 }
    ::= { tBgpPeerGroupEntry 17 }

tBgpPeerGroupMultihop            OBJECT-TYPE
    SYNTAX      BgpTimeToLive
    UNITS       "TTL hops"
    MAX-ACCESS  read-create
    STATUS      current
    DESCRIPTION
        "The value of tBgpPeerGroupMultihop specifies the TTL used in IP packet
         header for BGP advertisements.

         Default TTL values for EBGP peer is 1, and MAX_TTL for IBGP peers.
         Default value if not set is  no_type - the peer has to infer its value
         based on local-as, and peer-as in that case."
    DEFVAL      { 0 }
    ::= { tBgpPeerGroupEntry 18 }

tBgpPeerGroupNextHopSelf         OBJECT-TYPE
    SYNTAX      TruthValue
    MAX-ACCESS  read-create
    STATUS      current
    DESCRIPTION
        "The value of tBgpPeerGroupNextHopSelf specifies if routes advertised
         to EBGP peers in this group have NEXTHOP path attribute set to this
         router's physical interface.

         When false, third party routes are advertised."
    DEFVAL      { false }
    ::= { tBgpPeerGroupEntry 20 }

tBgpPeerGroupNoAggregatorID      OBJECT-TYPE
    SYNTAX      TruthValue
    MAX-ACCESS  read-create
    STATUS      current
    DESCRIPTION
        "The value of tBgpPeerGroupNoAggregatorID specifies if different
         routers in the same AS create aggregate routes containing different AS
         paths.

         A value of 'true' would enable setting the router ID to 0 in the
         aggregator path attribute when BGP is aggregating routes.

         A value of 'false' would disable setting the router ID to 0 in the
         aggregator path attribute when BGP is aggregating routes."
    DEFVAL      { false }
    ::= { tBgpPeerGroupEntry 21 }

tBgpPeerGroupPassive             OBJECT-TYPE
    SYNTAX      TruthValue
    MAX-ACCESS  read-create
    STATUS      current
    DESCRIPTION
        "The value of tBgpPeerGroupPassive specifies if the peers in this group
         will not attempt to connect to the far end peer or just wait for the
         far end peer to connect."
    DEFVAL      { false }
    ::= { tBgpPeerGroupEntry 22 }

tBgpPeerGroupPeerAS              OBJECT-TYPE
    SYNTAX      TmnxBgpAutonomousSystem
    MAX-ACCESS  read-create
    STATUS      obsolete
    DESCRIPTION
        "The value of tBgpPeerGroupPeerAS specifies the Autonomous System
         number for the remote peer.

         This object was obsoleted in release 7.0.  It is replaced with the
         4-byte AS number defined by tBgpPeerGroupPeerAS4Byte."
    DEFVAL      { 0 }
    ::= { tBgpPeerGroupEntry 23 }

tBgpPeerGroupPeerType            OBJECT-TYPE
    SYNTAX      BgpPeerType
    MAX-ACCESS  read-create
    STATUS      current
    DESCRIPTION
        "The value of tBgpPeerGroupPeerType specifies the type of peer -
         noType(1), internal(2) and external(3).

         Default value if not set is noType - the peer has to infer its value
         based on local-as, and peer-as in that case.

         If tBgpPeerGroupPeerAS4Byte is set to a non-default value, the value
         of the object tBgpPeerGroupPeerType is inferred from
         tBgpPeerGroupPeerAS4Byte regardless of the currently set value of
         tBgpPeerGroupPeerType."
    DEFVAL      { noType }
    ::= { tBgpPeerGroupEntry 24 }

tBgpPeerGroupPreference          OBJECT-TYPE
    SYNTAX      TmnxBgpPreference (1..255)
    MAX-ACCESS  read-create
    STATUS      current
    DESCRIPTION
        "The value of tBgpPeerGroupPreference specifies the route preference
         for routes learned via the peer."
    DEFVAL      { 170 }
    ::= { tBgpPeerGroupEntry 25 }

tBgpPeerGroupRemovePrivateAS     OBJECT-TYPE
    SYNTAX      TruthValue
    MAX-ACCESS  read-create
    STATUS      current
    DESCRIPTION
        "The value of tBgpPeerGroupRemovePrivateAS specifies if private AS
         numbers should be stripped from the AS Path before advertising them to
         BGP peers."
    DEFVAL      { false }
    ::= { tBgpPeerGroupEntry 26 }

tBgpPeerGroupLastChanged         OBJECT-TYPE
    SYNTAX      TimeStamp
    MAX-ACCESS  read-only
    STATUS      current
    DESCRIPTION
        "The value tBgpPeerGroupLastChanged indicates when an entry in
         tBgpPeerGroupTable was last changed."
    ::= { tBgpPeerGroupEntry 27 }

tBgpPeerGroupInheritance         OBJECT-TYPE
    SYNTAX      Counter64
    MAX-ACCESS  read-create
    STATUS      current
    DESCRIPTION
        "The value of tBgpPeerGroupInheritance specifies if the group entry in
         this row, should inherit the operational value of an object, or use
         the administratively set value.

         this object is a bit-mask, with the following positions:

         tBgpPeerGroupShutdown                            0x04
         tBgpPeerGroupConnectRetry                        0x10
         tBgpPeerGroupHoldTime                            0x20
         tBgpPeerGroupKeepAlive                           0x40
         tBgpPeerGroupDampening                          0x100
         tBgpPeerGroupLocalAS4Byte                       0x400
         tBgpPeerGroupLocalPreference                    0x800
         tBgpPeerGroupLoopDetect                        0x1000
         tBgpPeerGroupMinRouteAdvertisement             0x2000
         tBgpPeerGroupMEDSource                         0x8000
         tBgpPeerGroupMEDValue                         0x10000
         tBgpPeerGroupMultihop                         0x20000
         tBgpPeerGroupNoAggregatorID                  0x100000
         tBgpPeerGroupPreference                     0x1000000
         tBgpPeerGroupRemovePrivateAS                0x2000000
         tBgpPeerGroupImportPolicy1                  0x8000000
         tBgpPeerGroupExportPolicy1                0x100000000
         tBgpPeerGroupLocalASPrivate              0x2000000000
         tBgpPeerGroupMd5Auth                     0x4000000000
         tBgpPeerGroupMd5AuthKey                  0x8000000000
         tBgpPeerGroupClusterId                  0x10000000000
         tBgpPeerGroupDisableClientReflect       0x20000000000
         tBgpPeerGroupGracefulRestart            0x40000000000
         tBgpPeerGroupGRRestartTime              0x80000000000
         tBgpPeerGroupGRStaleRoute              0x100000000000
         tBgpPeerGroupGRAdminState              0x200000000000
         tBgpPeerGroupFamily                    0x400000000000
         tBgpPeerGroupVpnApplyImport            0x800000000000
         tBgpPeerGroupVpnApplyExport           0x1000000000000
         tBgpPeerGroupOrf                      0x4000000000000
         tBgpPeerGroupExtCommsOrf              0x8000000000000
         tBgpPeerGroupExtCommsSendOrf         0x10000000000000
         tBgpPeerGroupExtCommsRecvOrf         0x20000000000000
         tBgpPeerGroupDisable4ByteASN         0x80000000000000
         tBgpPeerGroupHoldTimeIsStrict       0x100000000000000
         tBgpPeerGroupRemovePrivateASLmtd    0x200000000000000
         tBgpPeerGroupPMTUDiscovery          0x400000000000000

         These named bits correspond to the names of objects in this table, but
         all import and export policy objects are represented by the same
         tBgpPeerGroupImportPolicy1/tBgpPeerGroupExportPolicy1 bit.

         When the bit for an object is set to one, then the object's
         administrative and operational value are whatever the DEFVAL or most
         recently SET value is.

         When the bit for an object is set to zero, then the object's
         administrative and operational value are inherited from the
         corresponding object in tBgpInstanceTable."
    DEFVAL      { 0 }
    ::= { tBgpPeerGroupEntry 28 }

tBgpPeerGroupImportPolicy1       OBJECT-TYPE
    SYNTAX      TPolicyStatementNameOrEmpty
    MAX-ACCESS  read-create
    STATUS      obsolete
    DESCRIPTION
        "The value of tBgpPeerGroupImportPolicy1 specifies import policy number
         1 for peer level.

         This object was obsoleted in release 10.0. It is replaced by object
         tBgpPeerGroupPlcyImportPolicy1."
    DEFVAL      { ''H }
    ::= { tBgpPeerGroupEntry 30 }

tBgpPeerGroupImportPolicy2       OBJECT-TYPE
    SYNTAX      TPolicyStatementNameOrEmpty
    MAX-ACCESS  read-create
    STATUS      obsolete
    DESCRIPTION
        "The value of tBgpPeerGroupImportPolicy2 specifies import policy number
         2 for peer level.

         This object was obsoleted in release 10.0. It is replaced by object
         tBgpPeerGroupPlcyImportPolicy2."
    DEFVAL      { ''H }
    ::= { tBgpPeerGroupEntry 31 }

tBgpPeerGroupImportPolicy3       OBJECT-TYPE
    SYNTAX      TPolicyStatementNameOrEmpty
    MAX-ACCESS  read-create
    STATUS      obsolete
    DESCRIPTION
        "The value of tBgpPeerGroupImportPolicy3 specifies import policy number
         3 for peer level.

         This object was obsoleted in release 10.0. It is replaced by object
         tBgpPeerGroupPlcyImportPolicy3."
    DEFVAL      { ''H }
    ::= { tBgpPeerGroupEntry 32 }

tBgpPeerGroupImportPolicy4       OBJECT-TYPE
    SYNTAX      TPolicyStatementNameOrEmpty
    MAX-ACCESS  read-create
    STATUS      obsolete
    DESCRIPTION
        "The value of tBgpPeerGroupImportPolicy4 specifies import policy number
         4 for peer level.

         This object was obsoleted in release 10.0. It is replaced by object
         tBgpPeerGroupPlcyImportPolicy4."
    DEFVAL      { ''H }
    ::= { tBgpPeerGroupEntry 33 }

tBgpPeerGroupImportPolicy5       OBJECT-TYPE
    SYNTAX      TPolicyStatementNameOrEmpty
    MAX-ACCESS  read-create
    STATUS      obsolete
    DESCRIPTION
        "The value of tBgpPeerGroupImportPolicy5 specifies import policy number
         5 for peer level.

         This object was obsoleted in release 10.0. It is replaced by object
         tBgpPeerGroupPlcyImportPolicy5."
    DEFVAL      { ''H }
    ::= { tBgpPeerGroupEntry 34 }

tBgpPeerGroupExportPolicy1       OBJECT-TYPE
    SYNTAX      TPolicyStatementNameOrEmpty
    MAX-ACCESS  read-create
    STATUS      obsolete
    DESCRIPTION
        "The value of tBgpPeerGroupExportPolicy1 specifies export policy number
         1 for peer level.

         This object was obsoleted in release 10.0. It is replaced by object
         tBgpPeerGroupPlcyExportPolicy1."
    DEFVAL      { ''H }
    ::= { tBgpPeerGroupEntry 35 }

tBgpPeerGroupExportPolicy2       OBJECT-TYPE
    SYNTAX      TPolicyStatementNameOrEmpty
    MAX-ACCESS  read-create
    STATUS      obsolete
    DESCRIPTION
        "The value of tBgpPeerGroupExportPolicy2 specifies export policy number
         2 for peer level.

         This object was obsoleted in release 10.0. It is replaced by object
         tBgpPeerGroupPlcyExportPolicy2."
    DEFVAL      { ''H }
    ::= { tBgpPeerGroupEntry 36 }

tBgpPeerGroupExportPolicy3       OBJECT-TYPE
    SYNTAX      TPolicyStatementNameOrEmpty
    MAX-ACCESS  read-create
    STATUS      obsolete
    DESCRIPTION
        "The value of tBgpPeerGroupExportPolicy3 specifies export policy number
         3 for peer level.

         This object was obsoleted in release 10.0. It is replaced by object
         tBgpPeerGroupPlcyExportPolicy3."
    DEFVAL      { ''H }
    ::= { tBgpPeerGroupEntry 37 }

tBgpPeerGroupExportPolicy4       OBJECT-TYPE
    SYNTAX      TPolicyStatementNameOrEmpty
    MAX-ACCESS  read-create
    STATUS      obsolete
    DESCRIPTION
        "The value of tBgpPeerGroupExportPolicy4 specifies export policy number
         4 for peer level.

         This object was obsoleted in release 10.0. It is replaced by object
         tBgpPeerGroupPlcyExportPolicy4."
    DEFVAL      { ''H }
    ::= { tBgpPeerGroupEntry 38 }

tBgpPeerGroupExportPolicy5       OBJECT-TYPE
    SYNTAX      TPolicyStatementNameOrEmpty
    MAX-ACCESS  read-create
    STATUS      obsolete
    DESCRIPTION
        "The value of tBgpPeerGroupExportPolicy5 specifies export policy number
         5 for peer level.

         This object was obsoleted in release 10.0. It is replaced by object
         tBgpPeerGroupPlcyExportPolicy5."
    DEFVAL      { ''H }
    ::= { tBgpPeerGroupEntry 39 }

tBgpPeerGroupOperStatus          OBJECT-TYPE
    SYNTAX      BgpOperState
    MAX-ACCESS  read-only
    STATUS      current
    DESCRIPTION
        "The value of tBgpPeerGroupOperStatus indicates the operational status
         of this BGP Group for the virtual router.

         A value of 'inService(2)' means the bgp group is fully functional.

         A value of 'outOfService(3)' means the bgp group is down.

         A value of 'transition(4)' means the bgp group is performing a
         transition from state inService(2) to outOfService(3) or vice versa.

         A value of 'disabled(5)' means the BGP group needs to be restarted by
         the user."
    ::= { tBgpPeerGroupEntry 40 }

tBgpPeerGroupLocalASPrivate      OBJECT-TYPE
    SYNTAX      TruthValue
    MAX-ACCESS  read-create
    STATUS      current
    DESCRIPTION
        "The value of tBgpPeerGroupLocalASPrivate specifies if the local
         autonomous system number is hidden in paths learned from peering.

         When the value of tBgpPeerGroupLocalAS4Byte is changed, the value of
         tBgpPeerGroupLocalASPrivate is reset to its default value.

         An 'inconsistentValue' error is returned if an attempt is made to set
         this object to a non-default value when the value of object
         tBgpPeerGroupLocalAS4Byte is not set to non-default value."
    DEFVAL      { false }
    ::= { tBgpPeerGroupEntry 41 }

tBgpPeerGroupMd5Auth             OBJECT-TYPE
    SYNTAX      TruthValue
    MAX-ACCESS  read-create
    STATUS      current
    DESCRIPTION
        "The value of tBgpPeerGroupMd5Auth specifies if the authentication
         using MD5 message based digest protocol is enabled."
    DEFVAL      { false }
    ::= { tBgpPeerGroupEntry 42 }

tBgpPeerGroupMd5AuthKey          OBJECT-TYPE
    SYNTAX      DisplayString (SIZE (0..255))
    MAX-ACCESS  read-create
    STATUS      current
    DESCRIPTION
        "The value of tBgpPeerGroupMd5AuthKey specifies the authentication key
         to be used between BGP peers neighbors before establishing sessions.

         Authentication is done using the MD5 message based digest protocol.

         Authentication can be configured globally and applied to all BGP peers
         or per group or per peer. The most specific value is used.

         The authentication key can be any combination of letters or numbers.
         Note that the string CANNOT contain embedded nulls."
    DEFVAL      { ''H }
    ::= { tBgpPeerGroupEntry 43 }

tBgpPeerGroupClusterId           OBJECT-TYPE
    SYNTAX      IpAddress
    MAX-ACCESS  read-create
    STATUS      current
    DESCRIPTION
        "This value of tBgpPeerGroupClusterId specifies the cluster ID for a
         route reflector server.

         A value of 0.0.0.0 indicates that no cluster ID has been assigned to
         the BGP group."
    DEFVAL      { '00000000'H }
    ::= { tBgpPeerGroupEntry 44 }

tBgpPeerGroupDisableClientReflect OBJECT-TYPE
    SYNTAX      TruthValue
    MAX-ACCESS  read-create
    STATUS      current
    DESCRIPTION
        "The value of tBgpPeerGroupDisableClientReflect specifies if reflection
         of routes by the route reflector to all client peers within its
         cluster is enabled or disabled.

         A value of 'false' means reflection of routes to all client peers is
         enabled."
    DEFVAL      { false }
    ::= { tBgpPeerGroupEntry 45 }

tBgpPeerGroupGracefulRestart     OBJECT-TYPE
    SYNTAX      TruthValue
    MAX-ACCESS  read-create
    STATUS      current
    DESCRIPTION
        "The value of tBgpPeerGroupGracefulRestart specifies whether or not
         graceful restart capabilities are enabled on this instance of BGP.

         When the value is set to 'false' graceful restart is disabled and any
         previous configuration of other graceful restart parameters is
         removed."
    DEFVAL      { false }
    ::= { tBgpPeerGroupEntry 46 }

tBgpPeerGroupGRRestartTime       OBJECT-TYPE
    SYNTAX      Unsigned32 (0..4095)
    UNITS       "seconds"
    MAX-ACCESS  read-create
    STATUS      current
    DESCRIPTION
        "The value of tBgpPeerGroupGRRestartTime specifies the maximum amount
         of time in seconds that a graceful restart should take."
    DEFVAL      { 300 }
    ::= { tBgpPeerGroupEntry 47 }

tBgpPeerGroupGRStaleRoute        OBJECT-TYPE
    SYNTAX      Unsigned32 (1..3600)
    UNITS       "seconds"
    MAX-ACCESS  read-create
    STATUS      current
    DESCRIPTION
        "The value of tBgpPeerGroupGRStaleRoute specifies the maximum amount of
         time in seconds that stale routes should be maintained after a
         graceful restart is initiated. This value should be at least as large
         as the value of tBgpPeerGroupGRRestartTime."
    DEFVAL      { 360 }
    ::= { tBgpPeerGroupEntry 48 }

tBgpPeerGroupGRAdminState        OBJECT-TYPE
    SYNTAX      TmnxAdminState
    MAX-ACCESS  read-create
    STATUS      current
    DESCRIPTION
        "The value of tBgpPeerGroupGRAdminState specifies the desired
         administrative state of the graceful restart capabilities for
         this peer group of the BGP protocol.  When the value is 'outOfService'
         the graceful restart capabilities are disabled but the
         graceful restart configuration parameters are retained."
    DEFVAL      { inService }
    ::= { tBgpPeerGroupEntry 49 }

tBgpPeerGroupGROperState         OBJECT-TYPE
    SYNTAX      TmnxOperState
    MAX-ACCESS  read-only
    STATUS      current
    DESCRIPTION
        "The value of tBgpPeerGroupGROperState indicates the operational status
         of the graceful restart capabilities for this peer group of the BGP
         protocol."
    ::= { tBgpPeerGroupEntry 50 }

tBgpPeerGroupFamily              OBJECT-TYPE
    SYNTAX      TmnxIpFamily
    MAX-ACCESS  read-create
    STATUS      current
    DESCRIPTION
        "The value of tBgpPeerGroupFamily specifies the types of routing
         information to be distributed by this peer group of BGP.  BGP was
         initially designed for the distribution of IPv4 routing information.
         Multi-protocol extensions and the use of a VPN-IPv4, VPN-IPv6, MVPN-IPv4
         and L2-VPN addresses have been added to extend its ability to carry
         overlapping routing information.

         A 'vpnIpv4 (2)' address is a 12-byte value consisting of
         the 8-byte route distinguisher, RD, and the 4-byte ipv4 IP address
         prefix.  The RD must be unique within the scope of the VPRN.
         This allows the IP address prefixes within different VRFs to
         overlap.

         'ipv6 (3)', 'mcastIpv4 (4)', 'l2vpn (6)' and 'mcastVpnIpv4 (12)' are
         multi-protocol extensions to BGP.

         'mcastIpv6 (16)' is part of multi-protocol extension to BGP.

         A 'vpnIpv6 (5)' address is a 24-byte value consisting of the 8-byte
         RD, and 16 bytes for the IPv6 address. When both IPv4 and IPv6 VPRN
         services are enabled, the PE router uses the same RD for both address
         families.

         A 'l2vpn (6)' address is a 12-byte Virtual Switch Instance identifier
         (VSI-ID) value consisting of the 8-byte route distinguisher(RD)
         followed by a 4-byte value.

         A 'mvpnIpv4  (7)' address is variable size value consisting of the
         1-byte route type, 1-byte length and variable size route type specific.
         Route type defines encoding for the route type specific field. Length
         indicates the length in octets of the route type specific field.

         A 'mdtSafi (8)' address is a 16-byte value consisting of 12-byte route
         distinguisher(RD) followed by a 4-byte group address.

         A 'mspw (9)' address is a dynamic multi-segment pseudowire address.

         A 'flowIpv4 (10)' address is a variable size value consisting of 1 or
         2-byte NLRI(Network Layer Reachability Information) length followed by
         a variable length NLRI value.

         A 'routeTarget (11)' address is a variable size value consisting of
         zero length or 12 byte (ipv4) or 24 byte (ipv6) NLRI (Network Layer
         Reachability Information) length followed by a variable length NLRI
         value.

         A 'mvpnIpv6 (13)' address is variable size value consisting of the
         1-byte route type, 1-byte length and variable size route type
         specific. Route type defines encoding for the route type specific
         field. Length indicates the length in octets of the route type
         specific field.

         A 'flowIpv6 (14)' address is a variable size value consisting of 1 or
         2-byte NLRI(Network Layer Reachability Information) length followed by
         a variable length NLRI value.

         A 'evpn (15)' address is variable size value consisting of the 1-byte
         route type, 1-byte length and variable size route type specific. Route
         type defines encoding for the route type specific field. Length
         indicates the length in octets of the route type specific field."
    DEFVAL      { {ipv4} }
    ::= { tBgpPeerGroupEntry 51 }

tBgpPeerGroupVpnApplyImport      OBJECT-TYPE
    SYNTAX      TruthValue
    MAX-ACCESS  read-create
    STATUS      current
    DESCRIPTION
        "The value of tBgpPeerGroupVpnApplyImport specifies if the BGP import
         route policies are applied to VPN-IPv4 routes of this group.

         When the value is 'false'  the application of the base instance
         BGP import route policies to VPN-IPv4 routes of this group is disabled."
    DEFVAL      { false }
    ::= { tBgpPeerGroupEntry 52 }

tBgpPeerGroupVpnApplyExport      OBJECT-TYPE
    SYNTAX      TruthValue
    MAX-ACCESS  read-create
    STATUS      current
    DESCRIPTION
        "The value of tBgpPeerGroupVpnApplyExport specifies if the BGP export
         route policies are applied to VPN-IPv4 routes of this group.

         When the value is 'false'  the application of the BGP export route
         policies to VPN-IPv4 routes of this group is disabled."
    DEFVAL      { false }
    ::= { tBgpPeerGroupEntry 53 }

tBgpPeerGroupASOverride          OBJECT-TYPE
    SYNTAX      TruthValue
    MAX-ACCESS  read-create
    STATUS      current
    DESCRIPTION
        "The value of tBgpPeerGroupASOverride specifies if the service provider
         BGP will override the customer AS number in the ASPATH with its own AS
         number.

         A value of 'true' means the service provider BGP will override the
         customer AS number in the ASPATH with its own AS number.

         Without this feature there could be scenarios where multiple CE
         locations belonging to the same AS will not be able to communicate due
         to a potential loop detection."
    DEFVAL      { false }
    ::= { tBgpPeerGroupEntry 54 }

tBgpPeerGroupOrf                 OBJECT-TYPE
    SYNTAX      TruthValue
    MAX-ACCESS  read-create
    STATUS      current
    DESCRIPTION
        "The value of tBgpPeerGroupOrf specifies if outbound route filtering
         capability is enabled or disabled for the BGP group."
    DEFVAL      { false }
    ::= { tBgpPeerGroupEntry 55 }

tBgpPeerGroupExtCommsOrf         OBJECT-TYPE
    SYNTAX      TruthValue
    MAX-ACCESS  read-create
    STATUS      current
    DESCRIPTION
        "The value of tBgpPeerGroupExtCommsOrf specifies if outbound route
         filtering capability is based on extended communities for the BGP
         group."
    DEFVAL      { false }
    ::= { tBgpPeerGroupEntry 56 }

tBgpPeerGroupExtCommsSendOrf     OBJECT-TYPE
    SYNTAX      TruthValue
    MAX-ACCESS  read-create
    STATUS      current
    DESCRIPTION
        "The value of tBgpPeerGroupExtCommsSendOrf specifies if outbound route
         filter advertisement to the neighbors in this BGP group."
    DEFVAL      { false }
    ::= { tBgpPeerGroupEntry 57 }

tBgpPeerGroupExtCommsRecvOrf     OBJECT-TYPE
    SYNTAX      TruthValue
    MAX-ACCESS  read-create
    STATUS      current
    DESCRIPTION
        "The value of tBgpPeerGroupExtCommsRecvOrf specifies if outbound route
         filter for this BGP group is accepted from the neighbors is enabled."
    DEFVAL      { false }
    ::= { tBgpPeerGroupEntry 58 }

tBgpPeerGroupDynamicPeerGroup    OBJECT-TYPE
    SYNTAX      TruthValue
    MAX-ACCESS  read-create
    STATUS      current
    DESCRIPTION
        "The value of tBgpPeerGroupDynamicPeerGroup specifies whether or not
         this peer group is dedicated to containing dynamically created peers.

         A value for this object can only be set during row creation.

         When set to TRUE it will not be possible to configure bgp peers in
         this group."
    DEFVAL      { false }
    ::= { tBgpPeerGroupEntry 59 }

tBgpPeerGroupLocalAS4Byte        OBJECT-TYPE
    SYNTAX      InetAutonomousSystemNumber
    MAX-ACCESS  read-create
    STATUS      current
    DESCRIPTION
        "The value of tBgpPeerGroupLocalAS4Byte specifies the autonomous system
         number to be advertised to this peer."
    DEFVAL      { 0 }
    ::= { tBgpPeerGroupEntry 60 }

tBgpPeerGroupPeerAS4Byte         OBJECT-TYPE
    SYNTAX      InetAutonomousSystemNumber
    MAX-ACCESS  read-create
    STATUS      current
    DESCRIPTION
        "The value of tBgpPeerGroupPeerAS4Byte specifies the autonomous system
         number for the remote peer."
    DEFVAL      { 0 }
    ::= { tBgpPeerGroupEntry 61 }

tBgpPeerGroupDisable4ByteASN     OBJECT-TYPE
    SYNTAX      TruthValue
    MAX-ACCESS  read-create
    STATUS      current
    DESCRIPTION
        "The value of tBgpPeerGroupDisable4ByteASN specifies whether or not
         4-byte ASN capability will be advertised by this peer.

         When the value of tBgpPeerGroupDisable4ByteASN is set to false, 4-byte
         ASN support will be negotiated with the associated remote peers. When
         the value of tBgpPeerGroupDisable4ByteASN is set to true, 4-byte ASN
         capability will not be advertised by this peer."
    DEFVAL      { false }
    ::= { tBgpPeerGroupEntry 62 }

tBgpPeerGroupHoldTimeIsStrict    OBJECT-TYPE
    SYNTAX      TruthValue
    MAX-ACCESS  read-create
    STATUS      obsolete
    DESCRIPTION
        "The value of tBgpPeerGroupHoldTimeIsStrict specifies whether or not
         tBgpPeerGroupHoldTime has to be strictly enforced.

         When the value of tBgpPeerGroupHoldTimeIsStrict is true, this BGP peer
         group will not negotiate a hold time lower than the configured value
         for tBgpPeerGroupHoldTime.

         This object is obsoleted in release 10.0. Desired functionality of
         strict enforcement of hold time can be achieved by configuring the
         value of tBgpPGMinHoldTime."
    DEFVAL      { false }
    ::= { tBgpPeerGroupEntry 63 }

tBgpPeerGroupRemovePrivateASLmtd OBJECT-TYPE
    SYNTAX      TruthValue
    MAX-ACCESS  read-create
    STATUS      current
    DESCRIPTION
        "The value of tBgpPeerGroupRemovePrivateASLmtd specifies whether BGP
         will remove the private AS numbers for this group.

         When the value of tBgpPeerGroupRemovePrivateASLmtd is true, BGP will
         remove private AS numbers from the AS Path for this group.

         When the value of tBgpPeerGroupRemovePrivateAS is changed, the value
         of tBgpPeerGroupRemovePrivateASLmtd is reset to its default value.

         An 'inconsistentValue' error is returned if an attempt is made to set
         this object to its default value. This object can be reset by
         resetting appropriate inheritance bit of tBgpPeerGroupInheritance."
    DEFVAL      { false }
    ::= { tBgpPeerGroupEntry 64 }

tBgpPeerGroupPMTUDiscovery       OBJECT-TYPE
    SYNTAX      TruthValue
    MAX-ACCESS  read-create
    STATUS      current
    DESCRIPTION
        "The value of tBgpPeerGroupPMTUDiscovery specifies whether path MTU
         discovery is enabled for this group.

         When the value is set to 'true', path MTU discovery is enabled for
         this group. When the value is set to 'false', path MTU discovery is
         disabled for this group."
    DEFVAL      { false }
    ::= { tBgpPeerGroupEntry 65 }

tBgpPeerGroupMaxPrefixLogOnly    OBJECT-TYPE
    SYNTAX      TruthValue
    MAX-ACCESS  read-create
    STATUS      obsolete
    DESCRIPTION
        "The value of tBgpPeerGroupMaxPrefixLogOnly specifies whether BGP
         peering will be disabled when tBgpPeerGroupMaxPrefix is exceeded.

         When the value is set to 'true', BGP peering will be enabled.

         When the value is set to 'false', BGP peering will be disabled.

         This object was obsoleted in release 13.0."
    DEFVAL      { false }
    ::= { tBgpPeerGroupEntry 66 }

tBgpPeerGroupMaxPrefixThreshold  OBJECT-TYPE
    SYNTAX      Unsigned32 (1..100)
    UNITS       "percent"
    MAX-ACCESS  read-create
    STATUS      obsolete
    DESCRIPTION
        "The value of tBgpPeerGroupMaxPrefixThreshold specifies a percentage of
         tBgpPeerGroupMaxPrefix.

         This object was obsoleted in release 13.0."
    DEFVAL      { 90 }
    ::= { tBgpPeerGroupEntry 67 }

tBgpPeerGroupDisableCapNego      OBJECT-TYPE
    SYNTAX      TruthValue
    MAX-ACCESS  read-create
    STATUS      current
    DESCRIPTION
        "The value of tBgpPeerGroupDisableCapNego specifies whether capability
         negotiation is disabled for this group."
    DEFVAL      { false }
    ::= { tBgpPeerGroupEntry 68 }

tBgpPeerGroupCreationOrigin      OBJECT-TYPE
    SYNTAX      TmnxCreateOrigin
    MAX-ACCESS  read-only
    STATUS      current
    DESCRIPTION
        "The value of tBgpPeerGroupCreationOrigin indicates the mechanism that
         created this group."
    ::= { tBgpPeerGroupEntry 69 }

tBgpPGSendOrfRouteTargetTable    OBJECT-TYPE
    SYNTAX      SEQUENCE OF TBgpPGSendOrfRouteTargetEntry
    MAX-ACCESS  not-accessible
    STATUS      current
    DESCRIPTION
        "Information about the route targets to be advertised to the peers if
         ORF is enabled for this peer group."
    ::= { tBgpPeerGroupObjects 4 }

tBgpPGSendOrfRouteTargetEntry    OBJECT-TYPE
    SYNTAX      TBgpPGSendOrfRouteTargetEntry
    MAX-ACCESS  not-accessible
    STATUS      current
    DESCRIPTION
        "An entry in the tBgpPGSendOrfRouteTargetTable. Each entry represents a
         route target to be advertised to the peers in this group."
    INDEX       {
        tBgpInstanceIndex,
        tBgpPeerGroupName,
        IMPLIED tBgpPGSendOrfRouteTarget
    }
    ::= { tBgpPGSendOrfRouteTargetTable 1 }

TBgpPGSendOrfRouteTargetEntry    ::= SEQUENCE
{
    tBgpPGSendOrfRouteTarget         TNamedItem,
    tBgpPGSendOrfRTRowStatus         RowStatus
}

tBgpPGSendOrfRouteTarget         OBJECT-TYPE
    SYNTAX      TNamedItem
    MAX-ACCESS  not-accessible
    STATUS      current
    DESCRIPTION
        "Index for the tBgpPGSendOrfRouteTargetTable. The value of
         tBgpPGSendOrfRouteTarget specifies the extended community name to be
         advertised to the peer."
    ::= { tBgpPGSendOrfRouteTargetEntry 1 }

tBgpPGSendOrfRTRowStatus         OBJECT-TYPE
    SYNTAX      RowStatus
    MAX-ACCESS  read-create
    STATUS      current
    DESCRIPTION
        "RowStatus for the Send Orf Route target entry."
    ::= { tBgpPGSendOrfRouteTargetEntry 2 }

tBgpPeerGroupParamsTable         OBJECT-TYPE
    SYNTAX      SEQUENCE OF TBgpPeerGroupParamsEntry
    MAX-ACCESS  not-accessible
    STATUS      current
    DESCRIPTION
        "Information about the attributes configured  for
         the BGP instance."
    ::= { tBgpPeerGroupObjects 5 }

tBgpPeerGroupParamsEntry         OBJECT-TYPE
    SYNTAX      TBgpPeerGroupParamsEntry
    MAX-ACCESS  not-accessible
    STATUS      current
    DESCRIPTION
        "An entry in the tBgpPeerGroupParamsTable. Each entry maintains the
         attributes configured for BGP instance."
    AUGMENTS    { tBgpPeerGroupEntry }
    ::= { tBgpPeerGroupParamsTable 1 }

TBgpPeerGroupParamsEntry         ::= SEQUENCE
{
    tBgpPGParamsInheritance          Counter64,
    tBgpPGDisableFEFailover          TruthValue,
    tBgpPGDisableComms               TruthValue,
    tBgpPGDisableExtComms            TruthValue,
    tBgpPGDefaultOriginate           TmnxIpFamily,
    tBgpPGAdvertiseInactiveRts       TruthValue,
    tBgpPGMinTTLValue                Unsigned32,
    tBgpPGTTLLogId                   TFilterLogId,
    tBgpPGLocalAddressType           InetAddressType,
    tBgpPGLocalAddress               InetAddress,
    tBgpPGPeerTracking               TruthValue,
    tBgpPGAuthKeyChain               TNamedItemOrEmpty,
    tBgpPGBfdEnabled                 TruthValue,
    tBgpPGEnableAddPath              TruthValue,
    tBgpPGRecvAddPath                TmnxAddPathAddressFamily,
    tBgpPGIpv4AddPathLimit           TmnxAddPathSendLimit,
    tBgpPGVpnIpv4AddPathLimit        TmnxAddPathSendLimit,
    tBgpPGIpv6AddPathLimit           TmnxAddPathSendLimit,
    tBgpPGVpnIpv6AddPathLimit        TmnxAddPathSendLimit,
    tBgpPGFlowspecValidate           TruthValue,
    tBgpPGUpdatedErrorHandling       TruthValue,
    tBgpPGDefaultRouteTarget         TruthValue,
    tBgpPGAigp                       TruthValue,
    tBgpPGMinHoldTime                BgpHoldTime,
    tBgpPGRemovePrivateSkipPeerAs    TruthValue,
    tBgpPGLocalASNoPrependGlobalAS   TruthValue,
    tBgpPGMaxPrefixIdleTimeOut       Integer32,
    tBgpPGGRRestartNotification      TruthValue,
    tBgpPGFaultTolerance             TruthValue,
    tBgpPGDampPeerOscillations       TruthValue,
    tBgpPGDampPeerOscInitialWaitTime Unsigned32,
    tBgpPGDampPeerOscSecondWaitTime  Unsigned32,
    tBgpPGDampPeerOscMaxWaitTime     Unsigned32,
    tBgpPGDampPeerOscErrorInterval   Unsigned32,
    tBgpPGSplitHorizon               TruthValue,
    tBgpPGNHUnchangedFamily          TmnxIpNhChgFamily,
    tBgpPGEnableOriginValidation     TmnxIpFamily,
    tBgpPGThirdPartyNextHop          TruthValue,
    tBgpPGAddLinkBandwidth           TmnxIpFamily,
    tBgpPGDynamicPeerLimit           Unsigned32,
    tBgpPGLabelResolveStatic         TruthValue,
    tBgpPGLblIpv4AddPathLimit        TmnxAddPathSendLimit,
    tBgpPGLblIpv6AddPathLimit        TmnxAddPathSendLimit,
    tBgpPGLabelPreference            TmnxBgpPreference,
    tBgpPGDefRxEvpnEncap             INTEGER,
    tBgpPGORRLocation                Unsigned32,
    tBgpPGORRAllowLocalFallbk        TruthValue,
    tBgpPGEnforceFirstAS             TruthValue,
    tBgpPGMvpnIpv4AddPathLimit       Integer32,
    tBgpPGMvpnIpv6AddPathLimit       Integer32,
    tBgpPGMcastVpnV4AddPathLimit     Integer32,
    tBgpPGMcastVpnV6AddPathLimit     Integer32,
    tBgpPGLLGRAdvStaleTime           Unsigned32,
    tBgpPGLLGROvrideStaleTime        Unsigned32,
    tBgpPGLLGROvrideResTime          Unsigned32,
    tBgpPGLLGRFwdingBitsSet          INTEGER,
    tBgpPGLLGRAdvStaleToNeigh        TruthValue,
    tBgpPGLLGRAdvToNeighWthoutNoEx   TruthValue,
    tBgpPGLLGR                       TruthValue,
    tBgpPGLocalAddressIfName         TNamedItemOrEmpty,
    tBgpPeerGroupAdvIpv6NhFamily     TmnxIpFamily,
    tBgpPGExtendNhEncoding           TmnxIpFamily,
    tBgpPGBypassMRAITimer            TruthValue,
    tBgpPGDisableLargeComms          TruthValue,
    tBgpPGEvpnAddPathLimit           TmnxAddPathSendLimit
}

tBgpPGParamsInheritance          OBJECT-TYPE
    SYNTAX      Counter64
    MAX-ACCESS  read-create
    STATUS      current
    DESCRIPTION
        "The value of tBgpPGParamsInheritance specifies if the peer entry in
         this row, should inherit the operational value of an object, or use
         the administratively set value.

         this object is a bit-mask, with the following positions:

         tBgpPGDisableFEFailover           0x0000000000000002
         tBgpPGDisableComms                0x0000000000000004
         tBgpPGDisableExtComms             0x0000000000000008
         $feature (TIMOS_FEATURE_BGP_DEFAULT_ORIGINATE)
         tBgpPGDefaultOriginate            0x0000000000000010
         }
         tBgpPGAdvertiseInactiveRts        0x0000000000000020
         tBgpPGPeerTracking                0x0000000000000400
         tBgpPGAuthKeyChain                0x0000000000000800
         tBgpPGBfdEnabled                  0x0000000000001000
         tBgpPGEnableAddPath               0x0000000000002000 #obsoleted 22.2
         tBgpPGRecvAddPath                 0x0000000000004000 #obsoleted 22.2
         tBgpPGIpv4AddPathLimit            0x0000000000008000 #obsoleted 22.2
         tBgpPGVpnIpv4AddPathLimit         0x0000000000010000 #obsoleted 22.2
         tBgpPGIpv6AddPathLimit            0x0000000000020000 #obsoleted 22.2
         tBgpPGVpnIpv6AddPathLimit         0x0000000000040000 #obsoleted 22.2
         tBgpPGFlowspecValidate            0x0000000000080000
         tBgpPGRemovePrivateSkipPeerAs     0x0000000001000000
         tBgpPGLocalASNoPrependGlobalAS    0x0000000002000000
         tBgpPGGRRestartNotification       0x0000000008000000
         tBgpPGFaultTolerance              0x0000000010000000
         tBgpPGDampPeerOscillations        0x0000000020000000
         tBgpPGSplitHorizon                0x0000000400000000
         tBgpPGThirdPartyNextHop           0x0000002000000000
         tBgpPGDynamicPeerLimit            0x0000008000000000
         tBgpPGLblIpv4AddPathLimit         0x0000020000000000 #obsoleted 22.2
         tBgpPGLblIpv6AddPathLimit         0x0000040000000000 #obsoleted 22.2
         tBgpPGLabelPreference             0x0000080000000000
         tBgpPGDefRxEvpnEncap              0x0000100000000000
         tBgpPGEnforceFirstAS              0x0000800000000000
         tBgpPGMvpnIpv4AddPathLimit        0x0001000000000000 #obsoleted 22.2
         tBgpPGMvpnIpv6AddPathLimit        0x0002000000000000 #obsoleted 22.2
         tBgpPGMcastVpnV4AddPathLimit      0x0004000000000000 #obsoleted 22.2
         tBgpPGMcastVpnV6AddPathLimit      0x0008000000000000 #obsoleted 22.2
         tBgpPGLLGR                        0x0400000000000000
         tBgpPGLocalAddressIfName          0x0800000000000000
         tBgpPeerGroupAdvIpv6NhFamily      0x1000000000000000
         tBgpPGExtendNhEncoding            0x2000000000000000
         tBgpPGBypassMRAITimer             0x4000000000000000
         tBgpPGDisableLargeComms           0x0800000000000000
         tBgpPGEvpnAddPathLimit            0x0010000000000000 #obsoleted 22.2
         When the bit for an object is set to one, then the
         object's administrative and operational value are whatever
         the DEFVAL or most recently SET value is.

         When the bit for an object is set to zero, then the object's
         administrative and operational value are inherited from the
         corresponding object in tBgpInstanceTable.

         By default all of these attributes should be inherited from the
         tBgpInstanceParamsTable."
    DEFVAL      { 0 }
    ::= { tBgpPeerGroupParamsEntry 1 }

tBgpPGDisableFEFailover          OBJECT-TYPE
    SYNTAX      TruthValue
    MAX-ACCESS  read-create
    STATUS      current
    DESCRIPTION
        "The value of tBgpPGDisableFEFailover controls whether the router
         should drop an external BGP session immediately when the local
         interface goes down, or whether the BGP session should be kept up
         until the holdtime expires.

         Setting the value to 'true' causes the external BGP session to go down
         immediately when the local interface goes down."
    DEFVAL      { false }
    ::= { tBgpPeerGroupParamsEntry 2 }

tBgpPGDisableComms               OBJECT-TYPE
    SYNTAX      TruthValue
    MAX-ACCESS  read-create
    STATUS      current
    DESCRIPTION
        "The value of tBgpPGDisableComms enables or disables sending of
         community attribute to the peer for non-external communities."
    DEFVAL      { false }
    ::= { tBgpPeerGroupParamsEntry 3 }

tBgpPGDisableExtComms            OBJECT-TYPE
    SYNTAX      TruthValue
    MAX-ACCESS  read-create
    STATUS      current
    DESCRIPTION
        "The value of tBgpPGDisableExtComms enables or disables sending of
         community attribute to the peers for external communities."
    DEFVAL      { false }
    ::= { tBgpPeerGroupParamsEntry 4 }

tBgpPGDefaultOriginate           OBJECT-TYPE
    SYNTAX      TmnxIpFamily
    MAX-ACCESS  read-create
    STATUS      current
    DESCRIPTION
        "The value of tBgpPGDefaultOriginate specifies the types of AFI/SAFI
         for which SROS BGP will originate default route independent of the RTM
         default route."
    ::= { tBgpPeerGroupParamsEntry 5 }

tBgpPGAdvertiseInactiveRts       OBJECT-TYPE
    SYNTAX      TruthValue
    MAX-ACCESS  read-create
    STATUS      current
    DESCRIPTION
        "The value of tBgpPGAdvertiseInactiveRts enables or disables
         advertising of inactive BGP routes to other BGP peers."
    DEFVAL      { false }
    ::= { tBgpPeerGroupParamsEntry 6 }

tBgpPGMinTTLValue                OBJECT-TYPE
    SYNTAX      Unsigned32 (0 | 1..255)
    MAX-ACCESS  read-create
    STATUS      current
    DESCRIPTION
        "The value of tBgpPGMinTTLValue specifies the minimum TTL value for an
         incoming BGP packet.

         If tBgpPGMinTTLValue is set to zero (0), the TTL Security feature is
         disabled."
    DEFVAL      { 0 }
    ::= { tBgpPeerGroupParamsEntry 7 }

tBgpPGTTLLogId                   OBJECT-TYPE
    SYNTAX      TFilterLogId
    MAX-ACCESS  read-create
    STATUS      current
    DESCRIPTION
        "The value of tBgpPGTTLLogId specifies the filter log to use for
         packets that fail TTL security check. The value zero indicates that
         logging is disabled."
    DEFVAL      { 0 }
    ::= { tBgpPeerGroupParamsEntry 8 }

tBgpPGLocalAddressType           OBJECT-TYPE
    SYNTAX      InetAddressType
    MAX-ACCESS  read-create
    STATUS      current
    DESCRIPTION
        "The value of tBgpPGLocalAddressType specifies the address type of the
         peer group local address. tBgpPGLocalAddressType can be either
         unknown, ipv4 or ipv6."
    ::= { tBgpPeerGroupParamsEntry 9 }

tBgpPGLocalAddress               OBJECT-TYPE
    SYNTAX      InetAddress (SIZE (0|4|16))
    MAX-ACCESS  read-create
    STATUS      current
    DESCRIPTION
        "The value of tBgpPGLocalAddress specifies the address of the peer
         group local address.

         If the tBgpPGLocalAddressType is set to ipv4, then the local address
         is an ipv4 address, if the tBgpPGLocalAddressType is set to ipv6, the
         local address of the peer group is an ipv6 address.

         If local address is not set, tBgpPGLocalAddressType is set to unknown
         and tBgpPGLocalAddress returns a null string."
    ::= { tBgpPeerGroupParamsEntry 10 }

tBgpPGPeerTracking               OBJECT-TYPE
    SYNTAX      TruthValue
    MAX-ACCESS  read-create
    STATUS      current
    DESCRIPTION
        "The value of tBgpPGPeerTracking specifies whether tracking of BGP
         peers on this peer group is enabled. The default value of 'false'
         indicates that peer tracking on this group is disabled."
    DEFVAL      { false }
    ::= { tBgpPeerGroupParamsEntry 11 }

tBgpPGAuthKeyChain               OBJECT-TYPE
    SYNTAX      TNamedItemOrEmpty
    MAX-ACCESS  read-create
    STATUS      current
    DESCRIPTION
        "The value of tBgpPGAuthKeyChain specifies the
         keychain which will be used to sign and/or authenticate  the BGP
         protocol stream.

         The keychain name is defined by tmnxKeyChainName and is the index for
         TIMETRA-SECURITY-MIB::tmnxKeyChainTable"
    DEFVAL      { ''H }
    ::= { tBgpPeerGroupParamsEntry 12 }

tBgpPGBfdEnabled                 OBJECT-TYPE
    SYNTAX      TruthValue
    MAX-ACCESS  read-create
    STATUS      current
    DESCRIPTION
        "The value of tBgpPGBfdEnabled specifies whether Bi-directional
         Forwarding Detection is enabled on this peer group.

         When the value is 'true', BFD sessions can be established and BFD can
         be used as a signalling mechanism."
    DEFVAL      { false }
    ::= { tBgpPeerGroupParamsEntry 13 }

tBgpPGEnableAddPath              OBJECT-TYPE
    SYNTAX      TruthValue
    MAX-ACCESS  read-create
    STATUS      obsolete
    DESCRIPTION
        "The value of tBgpPGEnableAddPath specifies whether the BGP ADD-PATH
         send capability is enabled on this BGP group.

         ADD-PATH allows a BGP router to advertise multiple distinct paths for
         the same prefix/NLRI(Network Layer Reachability Information). This
         capability provides a number of potential benefits like reduced
         routing churn, faster convergence, better loadsharing etc.

         When the value of tBgpPGEnableAddPath is set to 'true', the BGP
         ADD-PATH send limit objects tBgpPGIpv4AddPathLimit,
         tBgpPGVpnIpv4AddPathLimit, tBgpPGIpv6AddPathLimit,
         tBgpPGVpnIpv6AddPathLimit, tBgpPGLblIpv4AddPathLimit and
         tBgpPGLblIpv6AddPathLimit represent their current assigned values.

         The default value of tBgpPGEnableAddPath is 'false', which means the
         values of the BGP ADD-PATH send limit objects are inherited from from
         BGP instance level."
    DEFVAL      { false }
    ::= { tBgpPeerGroupParamsEntry 14 }

tBgpPGRecvAddPath                OBJECT-TYPE
    SYNTAX      TmnxAddPathAddressFamily
    MAX-ACCESS  read-create
    STATUS      obsolete
    DESCRIPTION
        "The value of tBgpPGRecvAddPath specifies the address families which
         are enabled to receive BGP ADD-PATH on this peer group.

         ADD-PATH allows a BGP router to receive multiple distinct paths for
         the same prefix/NLRI (Network Layer Reachability Information)."
    DEFVAL      { {none} }
    ::= { tBgpPeerGroupParamsEntry 15 }

tBgpPGIpv4AddPathLimit           OBJECT-TYPE
    SYNTAX      TmnxAddPathSendLimit
    MAX-ACCESS  read-create
    STATUS      obsolete
    DESCRIPTION
        "The value of tBgpPGIpv4AddPathLimit specifies the maximum number of
         paths per IPv4 prefix that can be advertised to ADD-PATH peers on this
         peer group.

         An 'inconsistentValue' error is returned if an attempt is made to set
         this object to a value greater than tBgpInstanceMultipathBgp."
    DEFVAL      { 0 }
    ::= { tBgpPeerGroupParamsEntry 16 }

tBgpPGVpnIpv4AddPathLimit        OBJECT-TYPE
    SYNTAX      TmnxAddPathSendLimit
    MAX-ACCESS  read-create
    STATUS      obsolete
    DESCRIPTION
        "The value of tBgpPGVpnIpv4AddPathLimit specifies the maximum number of
         paths per VPN IPv4 prefix that can be advertised to ADD-PATH peers on
         this peer group.

         An 'inconsistentValue' error is returned if an attempt is made to set
         this object to a value greater than tBgpInstanceMultipathBgp."
    DEFVAL      { 0 }
    ::= { tBgpPeerGroupParamsEntry 17 }

tBgpPGIpv6AddPathLimit           OBJECT-TYPE
    SYNTAX      TmnxAddPathSendLimit
    MAX-ACCESS  read-create
    STATUS      obsolete
    DESCRIPTION
        "The value of tBgpPGIpv6AddPathLimit specifies the maximum number of
         paths per IPv6 prefix that can be advertised to ADD-PATH peers on this
         peer group.

         An 'inconsistentValue' error is returned if an attempt is made to set
         this object to a value greater than tBgpInstanceMultipathBgp."
    DEFVAL      { 0 }
    ::= { tBgpPeerGroupParamsEntry 18 }

tBgpPGVpnIpv6AddPathLimit        OBJECT-TYPE
    SYNTAX      TmnxAddPathSendLimit
    MAX-ACCESS  read-create
    STATUS      obsolete
    DESCRIPTION
        "The value of tBgpPGVpnIpv6AddPathLimit specifies the maximum number of
         paths per VPN IPv6 prefix that can be advertised to ADD-PATH peers on
         this peer group.

         An 'inconsistentValue' error is returned if an attempt is made to set
         this object to a value greater than tBgpInstanceMultipathBgp."
    DEFVAL      { 0 }
    ::= { tBgpPeerGroupParamsEntry 19 }

tBgpPGFlowspecValidate           OBJECT-TYPE
    SYNTAX      TruthValue
    MAX-ACCESS  read-create
    STATUS      obsolete
    DESCRIPTION
        "The value of tBgpPGFlowspecValidate specifies whether validation of
         received flow specification routes is enabled for this peer group.

         When the value of tBgpPGFlowspecValidate is 'true', the flow routes
         received from other peers are validated.

         The default value of tBgpPGFlowspecValidate is 'false', which means
         validation of received flow routes is disabled and all flow
         specification routes are considered valid."
    DEFVAL      { false }
    ::= { tBgpPeerGroupParamsEntry 20 }

tBgpPGUpdatedErrorHandling       OBJECT-TYPE
    SYNTAX      TruthValue
    MAX-ACCESS  read-create
    STATUS      obsolete
    DESCRIPTION
        "The value of tBgpPGUpdatedErrorHandling specifies whether the error
         handling mechanism for optional transitive path attributes is enabled
         for this peer group.

         This object is obsoleted in release 11.0."
    DEFVAL      { false }
    ::= { tBgpPeerGroupParamsEntry 21 }

tBgpPGDefaultRouteTarget         OBJECT-TYPE
    SYNTAX      TruthValue
    MAX-ACCESS  read-create
    STATUS      current
    DESCRIPTION
        "The value of tBgpPGDefaultRouteTarget specifies whether to send the
         default Route Target Constraint (RTC) route to peers in this BGP peer
         group.

         The default RTC route is a special type of RTC route that has zero
         prefix length."
    DEFVAL      { false }
    ::= { tBgpPeerGroupParamsEntry 22 }

tBgpPGAigp                       OBJECT-TYPE
    SYNTAX      TruthValue
    MAX-ACCESS  read-create
    STATUS      current
    DESCRIPTION
        "The value of tBgpPGAigp specifies whether Accumulated IGP (AIGP) path
         attribute support is enabled on this bgp group.

         The default value of tBgpPGAigp is 'false', which means the AIGP
         attribute is removed from the advertised routes and is ignored if
         present in the received routes."
    DEFVAL      { false }
    ::= { tBgpPeerGroupParamsEntry 23 }

tBgpPGMinHoldTime                OBJECT-TYPE
    SYNTAX      BgpHoldTime
    MAX-ACCESS  read-create
    STATUS      current
    DESCRIPTION
        "The value of tBgpPGMinHoldTime specifies the minimum hold time that
         should be strictly enforced on tBgpPeerGroupHoldTime.

         When the value of tBgpPGMinHoldTime is configured, BGP will not
         negotiate a hold time lower than the configured value.

         When the value of tBgpPeerGroupHoldTime is changed, the value of
         tBgpPGMinHoldTime is reset to its default value.

         The value of tBgpPGMinHoldTime is inherited from the corresponding
         object value in the tBgpInstanceTable, when the inheritance bit for
         tBgpPeerGroupHoldTime is set to zero. An 'inconsistentValue' error is
         returned if an attempt is made to set this object to a non-default
         value when the value of tBgpPeerGroupHoldTime is inherited from
         instance level.

         An 'inconsistentValue' error is returned if an attempt is made to set
         this object to a value greater than tBgpPeerGroupHoldTime."
    DEFVAL      { 0 }
    ::= { tBgpPeerGroupParamsEntry 24 }

tBgpPGRemovePrivateSkipPeerAs    OBJECT-TYPE
    SYNTAX      TruthValue
    MAX-ACCESS  read-create
    STATUS      current
    DESCRIPTION
        "The value of tBgpPGRemovePrivateSkipPeerAs specifies whether or not to
         remove the private autonomous system number (ASN) from AS-Path, if the
         AS-Path contains the ASN of the external BGP (eBGP) neighbor on this
         BGP peer group.

         When the value of tBgpPGRemovePrivateSkipPeerAs is true, BGP will not
         remove the private ASN from the AS-Path if it is the same autonomous
         system number as the remote eBGP peer."
    DEFVAL      { false }
    ::= { tBgpPeerGroupParamsEntry 25 }

tBgpPGLocalASNoPrependGlobalAS   OBJECT-TYPE
    SYNTAX      TruthValue
    MAX-ACCESS  read-create
    STATUS      current
    DESCRIPTION
        "The value of tBgpPGLocalASNoPrependGlobalAS specifies whether or not
         to prepend the global-AS when advertising routes to the external BGP
         (eBGP) neighbor on this BGP peer group.

         When the value of tBgpPGLocalASNoPrependGlobalAS is true, BGP will
         prepend only the local-AS to the AS_PATH of received routes from the
         remote eBGP peer.

         When the value of tBgpPeerGroupLocalAS4Byte is changed, the value of
         tBgpPGLocalASNoPrependGlobalAS is reset to its default value.

         An 'inconsistentValue' error is returned if an attempt is made to set
         this object to a non-default value when the value of object
         tBgpPeerGroupLocalAS4Byte is not set to non-default value."
    DEFVAL      { false }
    ::= { tBgpPeerGroupParamsEntry 26 }

tBgpPGMaxPrefixIdleTimeOut       OBJECT-TYPE
    SYNTAX      Integer32 (0 | 1..1024)
    UNITS       "minutes"
    MAX-ACCESS  read-create
    STATUS      obsolete
    DESCRIPTION
        "The value of tBgpPGMaxPrefixIdleTimeOut specifies the idle time in
         minutes that the BGP peering remains disabled before attempting to
         automatically re-establish the connection with the peers in this BGP
         group after tBgpPeerGroupMaxPrefix limit is reached.

         The default value of tBgpPGMaxPrefixIdleTimeOut is zero which means,
         no attempt will be made to re-establish the BGP peering with peers in
         this BGP group after tBgpPeerGroupMaxPrefix limit is reached.

         When the value of tBgpPeerGroupMaxPrefix is changed, the value of
         tBgpPGMaxPrefixIdleTimeOut is reset to its default value.

         An 'inconsistentValue' error is returned if an attempt is made to set
         this object to a non-default value when the value of
         tBgpPeerGroupMaxPrefix is set to default value or the value of
         tBgpPeerGroupMaxPrefixLogOnly is set to non-default value.

         This object was obsoleted in release 13.0."
    DEFVAL      { 0 }
    ::= { tBgpPeerGroupParamsEntry 27 }

tBgpPGGRRestartNotification      OBJECT-TYPE
    SYNTAX      TruthValue
    MAX-ACCESS  read-create
    STATUS      current
    DESCRIPTION
        "The value of tBgpPGGRRestartNotification specifies whether or not to
         perform Graceful Restart procedures after sending or receiving a
         NOTIFICATION message from a peer in this BGP peer group.

         When the value of tBgpPGGRRestartNotification is true, BGP will
         perform Graceful Restart procedures after sending or receiving a
         NOTIFICATION message from a peer in this BGP peer group."
    DEFVAL      { false }
    ::= { tBgpPeerGroupParamsEntry 28 }

tBgpPGFaultTolerance             OBJECT-TYPE
    SYNTAX      TruthValue
    MAX-ACCESS  read-create
    STATUS      current
    DESCRIPTION
        "The value of tBgpPGFaultTolerance specifies whether or not approaches
         like 'treat-as-withdraw' and other similar non-disruptive approaches
         can be used for handling a wide range of UPDATE message errors.

         A value of 'false' indicates that bgp fault-tolerance is disabled on
         this BGP peer group."
    DEFVAL      { false }
    ::= { tBgpPeerGroupParamsEntry 29 }

tBgpPGDampPeerOscillations       OBJECT-TYPE
    SYNTAX      TruthValue
    MAX-ACCESS  read-create
    STATUS      current
    DESCRIPTION
        "The value of tBgpPGDampPeerOscillations specifies whether damping peer
         oscillations is enabled for this BGP peer group.

         When the value is set to 'true', damping peer oscillations is enabled
         for this BGP peer group. When the value is set to 'false', damping
         peer oscillations is disabled."
    DEFVAL      { false }
    ::= { tBgpPeerGroupParamsEntry 30 }

tBgpPGDampPeerOscInitialWaitTime OBJECT-TYPE
    SYNTAX      Unsigned32 (0..2048)
    UNITS       "minutes"
    MAX-ACCESS  read-create
    STATUS      current
    DESCRIPTION
        "The value of tBgpPGDampPeerOscInitialWaitTime specifies the time in
         minutes, that a session remains in the idle-state after it has been
         stable for a while for this BGP peer group.

         When the value of tBgpPGDampPeerOscillations is changed, the value of
         tBgpPGDampPeerOscInitialWaitTime is reset to its default value.

         The value of tBgpPGDampPeerOscInitialWaitTime is inherited from the
         corresponding object value in the tBgpInstanceParamsTable, when the
         inheritance bit for tBgpPGDampPeerOscillations is set to zero. An
         'inconsistentValue' error is returned if an attempt is made to set
         this object to a non-default value when the value of
         tBgpPGDampPeerOscillations is inherited from instance level.

         An 'inconsistentValue' error is returned if an attempt is made to set
         this object without setting tBgpPGDampPeerOscillations."
    DEFVAL      { 0 }
    ::= { tBgpPeerGroupParamsEntry 31 }

tBgpPGDampPeerOscSecondWaitTime  OBJECT-TYPE
    SYNTAX      Unsigned32 (1..2048)
    UNITS       "minutes"
    MAX-ACCESS  read-create
    STATUS      current
    DESCRIPTION
        "The value of tBgpPGDampPeerOscSecondWaitTime specifies the time in
         minutes, that is doubled after each repeated session failure that
         occurs within a relatively short span of time for this BGP peer group.

         When the value of tBgpPGDampPeerOscillations is changed, the value of
         tBgpPGDampPeerOscSecondWaitTime is reset to its default value.

         The value of tBgpPGDampPeerOscSecondWaitTime is inherited from the
         corresponding object value in the tBgpInstanceParamsTable, when the
         inheritance bit for tBgpPGDampPeerOscillations is set to zero. An
         'inconsistentValue' error is returned if an attempt is made to set
         this object to a non-default value when the value of
         tBgpPGDampPeerOscillations is inherited from instance level.

         An 'inconsistentValue' error is returned if an attempt is made to set
         this object without setting tBgpPGDampPeerOscillations."
    DEFVAL      { 5 }
    ::= { tBgpPeerGroupParamsEntry 32 }

tBgpPGDampPeerOscMaxWaitTime     OBJECT-TYPE
    SYNTAX      Unsigned32 (1..2048)
    UNITS       "minutes"
    MAX-ACCESS  read-create
    STATUS      current
    DESCRIPTION
        "The value of tBgpPGDampPeerOscMaxWaitTime specifies the maximum amount
         of time in minutes, that the session remains in the idle-state after
         it has experienced repeated instability for this BGP peer group.

         When the value of tBgpPGDampPeerOscillations is changed, the value of
         tBgpPGDampPeerOscMaxWaitTime is reset to its default value.

         The value of tBgpPGDampPeerOscMaxWaitTime is inherited from the
         corresponding object value in the tBgpInstanceParamsTable, when the
         inheritance bit for tBgpPGDampPeerOscillations is set to zero. An
         'inconsistentValue' error is returned if an attempt is made to set
         this object to a non-default value when the value of
         tBgpPGDampPeerOscillations is inherited from instance level.

         An 'inconsistentValue' error is returned if an attempt is made to set
         this object without setting tBgpPGDampPeerOscillations."
    DEFVAL      { 60 }
    ::= { tBgpPeerGroupParamsEntry 33 }

tBgpPGDampPeerOscErrorInterval   OBJECT-TYPE
    SYNTAX      Unsigned32 (0..2048)
    UNITS       "minutes"
    MAX-ACCESS  read-create
    STATUS      current
    DESCRIPTION
        "The value of tBgpPGDampPeerOscErrorInterval specifies the time in
         minutes, after a session reset, during which the session must be
         error-free in order to reset the penalty counter and return
         idle-hold-time to tBgpPGDampPeerOscInitialWaitTime for this BGP peer.

         When the value of tBgpPGDampPeerOscillations is changed, the value of
         tBgpPGDampPeerOscErrorInterval is reset to its default value.

         The value of tBgpPGDampPeerOscErrorInterval is inherited from the
         corresponding object value in the tBgpInstanceParamsTable, when the
         inheritance bit for tBgpPGDampPeerOscillations is set to zero. An
         'inconsistentValue' error is returned if an attempt is made to set
         this object to a non-default value when the value of
         tBgpPGDampPeerOscillations is inherited from instance level.

         An 'inconsistentValue' error is returned if an attempt is made to set
         this object without setting tBgpPGDampPeerOscillations."
    DEFVAL      { 30 }
    ::= { tBgpPeerGroupParamsEntry 34 }

tBgpPGSplitHorizon               OBJECT-TYPE
    SYNTAX      TruthValue
    MAX-ACCESS  read-create
    STATUS      current
    DESCRIPTION
        "The value of tBgpPGSplitHorizon specifies whether or not the peers
         under this group reflect the best route back to the peer from which
         the route was received.

         When the value of tBgpPGSplitHorizon is 'true', the peers under this
         group will not reflect best routes to the peers from which the route
         was received."
    DEFVAL      { false }
    ::= { tBgpPeerGroupParamsEntry 35 }

tBgpPGNHUnchangedFamily          OBJECT-TYPE
    SYNTAX      TmnxIpNhChgFamily
    MAX-ACCESS  read-create
    STATUS      current
    DESCRIPTION
        "The value of tBgpPGNHUnchangedFamily specifies the address families
         for which the BGP next-hop is not modified when sending routes to
         selected EBGP peers in this group.

         When the value of tBgpPGNHUnchangedFamily is set to 'labelIpv4', the
         next-hop attribute of an ebgp peer in this peer group remains
         unchanged.

         When the route is advertised to IBGP and confed-EBGP peers, the object
         tBgpPGNHUnchangedFamily has no effect on the routes, since nexthop
         unchanged is default functionality."
    DEFVAL      { {} }
    ::= { tBgpPeerGroupParamsEntry 36 }

tBgpPGEnableOriginValidation     OBJECT-TYPE
    SYNTAX      TmnxIpFamily
    MAX-ACCESS  read-create
    STATUS      current
    DESCRIPTION
        "The value of tBgpPGEnableOriginValidation specifies the address family
         for which every inbound IPv4 and/or IPv6 route from the peer is marked
         with either valid, not-found or invalid origin validation states.

         When the value of tBgpPGEnableOriginValidation is set to 'ipv4(1)',
         only the address family for ipv4 is evaluated.

         When the value of tBgpPGEnableOriginValidation is set to 'ipv6(3)',
         only the address family for ipv6 is evaluated.

         When the value of tBgpPGEnableOriginValidation is set to neither
         'ipv4(1)' and 'ipv6(3)' or when the value of
         tBgpPGEnableOriginValidation is set to both 'ipv4(1)' and 'ipv6(3)'
         all unicast IPv4 and IPv6 routes are evaluated to determine their
         origin validation states."
    DEFVAL      { {} }
    ::= { tBgpPeerGroupParamsEntry 37 }

tBgpPGThirdPartyNextHop          OBJECT-TYPE
    SYNTAX      TruthValue
    MAX-ACCESS  read-create
    STATUS      current
    DESCRIPTION
        "The value of tBgpPGThirdPartyNextHop specifies if there is any third
         party next-hop processing done towards single-hop EBGP peers in this
         group.

         When false, NEXT_HOP will always carry the IP address of the interface
         used to establish the TCP connection to the peer"
    DEFVAL      { false }
    ::= { tBgpPeerGroupParamsEntry 38 }

tBgpPGAddLinkBandwidth           OBJECT-TYPE
    SYNTAX      TmnxIpFamily
    MAX-ACCESS  read-create
    STATUS      current
    DESCRIPTION
        "The value of tBgpPGAddLinkBandwidth specifies the address families of
         the routes received from a single-hop EBGP neighbor, for which a Link
         Bandwidth Extended Community with static AS and bandwidth values is
         added.

         When the family of the received route matches the configured families
         in tBgpPGAddLinkBandwidth, a Link Bandwidth Extended Community is
         added, consisting of the local AS and interface speed."
    DEFVAL      { {} }
    ::= { tBgpPeerGroupParamsEntry 39 }

tBgpPGDynamicPeerLimit           OBJECT-TYPE
    SYNTAX      Unsigned32 (0 | 1..8192)
    MAX-ACCESS  read-create
    STATUS      current
    DESCRIPTION
        "The value of tBgpPGDynamicPeerLimit specifies the value of dynamic
         peer limit for this BGP group.

         If tBgpPGDynamicPeerLimit is set to zero (0), the dynamic peer limit
         is disabled for this BGP group."
    DEFVAL      { 0 }
    ::= { tBgpPeerGroupParamsEntry 40 }

tBgpPGLabelResolveStatic         OBJECT-TYPE
    SYNTAX      TruthValue
    MAX-ACCESS  read-create
    STATUS      obsolete
    DESCRIPTION
        "The value of tBgpPGLabelResolveStatic specifies whether multi-hop eBGP
         learned labeled IP routes to be resolved by IP routes if no LDP or
         RSVP-TE LSPs are available.

         Even if this behavior is enabled, LDP or RSVP-TE defined paths should
         first resolve the BGP nexthop for the labeled routes. Only if none are
         available should resolution to the IP route table be attempted."
    DEFVAL      { false }
    ::= { tBgpPeerGroupParamsEntry 41 }

tBgpPGLblIpv4AddPathLimit        OBJECT-TYPE
    SYNTAX      TmnxAddPathSendLimit
    MAX-ACCESS  read-create
    STATUS      obsolete
    DESCRIPTION
        "The value of tBgpPGLblIpv4AddPathLimit specifies the maximum number of
         paths per label IPv4 prefix that can be advertised to ADD-PATH peers
         on this peer group.

         An 'inconsistentValue' error is returned if an attempt is made to set
         this object to a value greater than tBgpInstanceMultipathBgp."
    DEFVAL      { 0 }
    ::= { tBgpPeerGroupParamsEntry 42 }

tBgpPGLblIpv6AddPathLimit        OBJECT-TYPE
    SYNTAX      TmnxAddPathSendLimit
    MAX-ACCESS  read-create
    STATUS      obsolete
    DESCRIPTION
        "The value of tBgpPGLblIpv6AddPathLimit specifies the maximum number of
         paths per label IPv6 prefix that can be advertised to ADD-PATH peers
         on this peer group.

         An 'inconsistentValue' error is returned if an attempt is made to set
         this object to a value greater than tBgpInstanceMultipathBgp."
    DEFVAL      { 0 }
    ::= { tBgpPeerGroupParamsEntry 43 }

tBgpPGLabelPreference            OBJECT-TYPE
    SYNTAX      TmnxBgpPreference (1..255)
    MAX-ACCESS  read-create
    STATUS      current
    DESCRIPTION
        "The value of tBgpPGLabelPreference specifies the route preference for
         label-IPv4 and label-IPv6 routes learned via the peer."
    DEFVAL      { 170 }
    ::= { tBgpPeerGroupParamsEntry 44 }

tBgpPGDefRxEvpnEncap             OBJECT-TYPE
    SYNTAX      INTEGER {
        mpls  (0),
        vxlan (1)
    }
    MAX-ACCESS  read-create
    STATUS      current
    DESCRIPTION
        "The value of tBgpPGDefRxEvpnEncap specifies how BGP will treat a
         received EVPN route without BGP encapsulation extended community. If
         no encapsulation is received, BGP will validate the route as MPLS or
         VXLAN depending on the the value of tBgpPGDefRxEvpnEncap."
    DEFVAL      { mpls }
    ::= { tBgpPeerGroupParamsEntry 45 }

tBgpPGORRLocation                OBJECT-TYPE
    SYNTAX      Unsigned32 (0..255)
    MAX-ACCESS  read-create
    STATUS      current
    DESCRIPTION
        "The value of tBgpPGORRLocation specifies the identifier of a location
         configured under optimal-route-reflection. The location is used to
         calculate the next-hop cost in the TE-DB and select the best path to
         advertise to the client of this route-reflector."
    DEFVAL      { 0 }
    ::= { tBgpPeerGroupParamsEntry 46 }

tBgpPGORRAllowLocalFallbk        OBJECT-TYPE
    SYNTAX      TruthValue
    MAX-ACCESS  read-create
    STATUS      current
    DESCRIPTION
        "The value of tBgpPGORRAllowLocalFallbk decides what the system should
         do when the BGP next-hop is not reachable in the TE-DB for the
         configured location, tBgpPGORRLocation.

         If the value is set to 'true', then next-hop cost calculation and
         best-path selection default back to the location of the
         route-reflector in the network.

         If the value is set to 'false', then no routes are advertised to the
         client(s)."
    DEFVAL      { false }
    ::= { tBgpPeerGroupParamsEntry 47 }

tBgpPGEnforceFirstAS             OBJECT-TYPE
    SYNTAX      TruthValue
    MAX-ACCESS  read-create
    STATUS      current
    DESCRIPTION
        "The value of tBgpPGEnforceFirstAS specifies whether the receipt of BGP
         routes from an eBGP neighbor should be classified as an error when it
         has an AS-Path with the most recent AS not matching the configured
         peer-as of the neighbor.

         If the value is set to 'true', the most recent AS number in the
         AS-Path will be checked for every received route from the peer or set
         of peers to match the peer's configured peer-as. If it does not match,
         then the session will be reset if the update-fault-tolerance under
         error-handling is not configured. Else, the session will not be reset,
         but all the prefixes in the received update will be treated as
         withdrawn and logged.

         It is applicable to all the address families and only to true eBGP
         sessions."
    DEFVAL      { false }
    ::= { tBgpPeerGroupParamsEntry 48 }

tBgpPGMvpnIpv4AddPathLimit       OBJECT-TYPE
    SYNTAX      Integer32 (0..16)
    MAX-ACCESS  read-create
    STATUS      obsolete
    DESCRIPTION
        "The value of tBgpPGMvpnIpv4AddPathLimit specifies the maximum number
         of paths per MVPN IPv4 prefix that can be advertised to ADD-PATH peers
         on this peer group.

         An 'inconsistentValue' error is returned if an attempt is made to set
         this object to a value greater than tBgpInstanceMultipathBgp."
    DEFVAL      { 0 }
    ::= { tBgpPeerGroupParamsEntry 49 }

tBgpPGMvpnIpv6AddPathLimit       OBJECT-TYPE
    SYNTAX      Integer32 (0..16)
    MAX-ACCESS  read-create
    STATUS      obsolete
    DESCRIPTION
        "The value of tBgpPGMvpnIpv6AddPathLimit specifies the maximum number
         of paths per VPN IPv6 prefix that can be advertised to ADD-PATH peers
         on this peer group.

         An 'inconsistentValue' error is returned if an attempt is made to set
         this object to a value greater than tBgpInstanceMultipathBgp."
    DEFVAL      { 0 }
    ::= { tBgpPeerGroupParamsEntry 50 }

tBgpPGMcastVpnV4AddPathLimit     OBJECT-TYPE
    SYNTAX      Integer32 (0..16)
    MAX-ACCESS  read-create
    STATUS      obsolete
    DESCRIPTION
        "The value of tBgpPGMcastVpnV4AddPathLimit specifies the maximum number
         of paths per Mcast VPN IPv4 prefix that can be advertised to ADD-PATH
         peers on this peer group.

         An 'inconsistentValue' error is returned if an attempt is made to set
         this object to a value greater than tBgpInstanceMultipathBgp."
    DEFVAL      { 0 }
    ::= { tBgpPeerGroupParamsEntry 51 }

tBgpPGMcastVpnV6AddPathLimit     OBJECT-TYPE
    SYNTAX      Integer32 (0..16)
    MAX-ACCESS  read-create
    STATUS      obsolete
    DESCRIPTION
        "The value of tBgpPGMcastVpnV6AddPathLimit specifies the maximum number
         of paths per Mcast VPN IPv6 prefix that can be advertised to ADD-PATH
         peers on this peer group.

         An 'inconsistentValue' error is returned if an attempt is made to set
         this object to a value greater than tBgpInstanceMultipathBgp."
    DEFVAL      { 0 }
    ::= { tBgpPeerGroupParamsEntry 52 }

tBgpPGLLGRAdvStaleTime           OBJECT-TYPE
    SYNTAX      Unsigned32 (0..16777215)
    MAX-ACCESS  read-create
    STATUS      current
    DESCRIPTION
        "The value of tBgpPGLLGRAdvStaleTime specifies the time value until
         when a route can be used after the session with the peer is
         disconnected"
    DEFVAL      { 86400 }
    ::= { tBgpPeerGroupParamsEntry 53 }

tBgpPGLLGROvrideStaleTime        OBJECT-TYPE
    SYNTAX      Unsigned32 (0..16777216)
    MAX-ACCESS  read-create
    STATUS      current
    DESCRIPTION
        "The value of tBgpPGLLGROvrideStaleTime specifies the stale time for
         the BGP session when it is in helper mode."
    DEFVAL      { 16777216 }
    ::= { tBgpPeerGroupParamsEntry 54 }

tBgpPGLLGROvrideResTime          OBJECT-TYPE
    SYNTAX      Unsigned32 (0..4096)
    MAX-ACCESS  read-create
    STATUS      current
    DESCRIPTION
        "The value of tBgpPGLLGROvrideResTime specifies the restart time for
         the BGP session when it is in helper mode."
    DEFVAL      { 4096 }
    ::= { tBgpPeerGroupParamsEntry 55 }

tBgpPGLLGRFwdingBitsSet          OBJECT-TYPE
    SYNTAX      INTEGER {
        none    (0),
        all     (1),
        non-fwd (2)
    }
    MAX-ACCESS  read-create
    STATUS      current
    DESCRIPTION
        "The value of tBgpPGLLGRFwdingBitsSet specifies the behaviour of the F
         bit for each AFI/SAFI."
    DEFVAL      { none }
    ::= { tBgpPeerGroupParamsEntry 56 }

tBgpPGLLGRAdvStaleToNeigh        OBJECT-TYPE
    SYNTAX      TruthValue
    MAX-ACCESS  read-create
    STATUS      current
    DESCRIPTION
        "The value of tBgpPGLLGRAdvStaleToNeigh decides whether to withdraw the
         route towards eBGP peers that did not advertise the LLGR capability
         and re-advertise to all other peers with the addition of the
         LLGR_STALE community."
    DEFVAL      { false }
    ::= { tBgpPeerGroupParamsEntry 57 }

tBgpPGLLGRAdvToNeighWthoutNoEx   OBJECT-TYPE
    SYNTAX      TruthValue
    MAX-ACCESS  read-create
    STATUS      current
    DESCRIPTION
        "The value of tBgpPGLLGRAdvToNeighWthoutNoEx decides whether to
         advertise the route to all peers with the addition of the LLGR_STALE
         community.

         This can be configured only when tBgpPGLLGRAdvStaleToNeigh is
         configured on the system."
    DEFVAL      { false }
    ::= { tBgpPeerGroupParamsEntry 58 }

tBgpPGLLGR                       OBJECT-TYPE
    SYNTAX      TruthValue
    MAX-ACCESS  read-create
    STATUS      current
    DESCRIPTION
        "The value of tBgpPGLLGR specifies whether or not long lived graceful
         restart capabilities are enabled on this instance of BGP.

         When the value is set to 'false' long lived graceful restart is
         disabled and any previous configuration of other long lived graceful
         restart parameters is removed."
    DEFVAL      { false }
    ::= { tBgpPeerGroupParamsEntry 59 }

tBgpPGLocalAddressIfName         OBJECT-TYPE
    SYNTAX      TNamedItemOrEmpty
    MAX-ACCESS  read-create
    STATUS      current
    DESCRIPTION
        "The value of tBgpPGLocalAddressIfName specifies the interface name of
         the peer group local address.

         Either tBgpPGLocalAddressIfName or tBgpPGLocalAddress can be set at a
         time. The other one is set to default."
    ::= { tBgpPeerGroupParamsEntry 60 }

tBgpPeerGroupAdvIpv6NhFamily     OBJECT-TYPE
    SYNTAX      TmnxIpFamily
    MAX-ACCESS  read-create
    STATUS      current
    DESCRIPTION
        "The value of tBgpPeerGroupAdvIpv6NhFamily specifies the types of
         AFI/SAFI the SROS BGP group supports extended next-hop encoding and
         resolution."
    ::= { tBgpPeerGroupParamsEntry 61 }

tBgpPGExtendNhEncoding           OBJECT-TYPE
    SYNTAX      TmnxIpFamily
    MAX-ACCESS  read-create
    STATUS      current
    DESCRIPTION
        "The value of tBgpPGExtendNhEncoding specifies the type of AFI/SAFI the
         Bgp group is configured to support extended next-hop encoding."
    ::= { tBgpPeerGroupParamsEntry 62 }

tBgpPGBypassMRAITimer            OBJECT-TYPE
    SYNTAX      TruthValue
    MAX-ACCESS  read-create
    STATUS      current
    DESCRIPTION
        "The value of tBgpPGBypassMRAITimer specifies whether the Bgp instance
         is configured to send out the BGP update immediately after the session
         comes up, without waiting for Minimum Route Advertisement Interval,
         tBgpPeerGroupMinRouteAdvertisement, to countdown to zero.

         If the value is set to 'true', tBgpPeerGroupMinRouteAdvertisement's
         value is disregarded and BGP updates are sent out immediately after
         the session comes up.

         If the value is set to 'false', the system waits for
         tBgpPeerGroupMinRouteAdvertisement's full value to countdown before
         sending out the BGP updates after the session comes up."
    DEFVAL      { false }
    ::= { tBgpPeerGroupParamsEntry 63 }

tBgpPGDisableLargeComms          OBJECT-TYPE
    SYNTAX      TruthValue
    MAX-ACCESS  read-create
    STATUS      current
    DESCRIPTION
        "The value of tBgpPGDisableLargeComms enables or disables sending of
         community attribute to the peer for large communities."
    DEFVAL      { false }
    ::= { tBgpPeerGroupParamsEntry 64 }

tBgpPGEvpnAddPathLimit           OBJECT-TYPE
    SYNTAX      TmnxAddPathSendLimit
    MAX-ACCESS  read-create
    STATUS      obsolete
    DESCRIPTION
        "The value of tBgpPGEvpnAddPathLimit specifies the maximum
         number of paths per EVPN  prefix that can be advertised to
         ADD-PATH peers on this peer group.

         An 'inconsistentValue' error is returned if an attempt is made to set
         this object to a value greater than tBgpInstanceMultipathBgp."
    DEFVAL      { 0 }
    ::= { tBgpPeerGroupParamsEntry 65 }

tBgpPeerGroupPlcyTable           OBJECT-TYPE
    SYNTAX      SEQUENCE OF TBgpPeerGroupPlcyEntry
    MAX-ACCESS  not-accessible
    STATUS      current
    DESCRIPTION
        "The tBgpPeerGroupPlcyTable is the list of configured policies in BGP
         Peer Groups."
    ::= { tBgpPeerGroupObjects 6 }

tBgpPeerGroupPlcyEntry           OBJECT-TYPE
    SYNTAX      TBgpPeerGroupPlcyEntry
    MAX-ACCESS  not-accessible
    STATUS      current
    DESCRIPTION
        "An entry (conceptual row) in the tBgpPeerGroupPlcyTable."
    AUGMENTS    { tBgpPeerGroupEntry }
    ::= { tBgpPeerGroupPlcyTable 1 }

TBgpPeerGroupPlcyEntry           ::= SEQUENCE
{
    tBgpPeerGroupPlcyImportPolicy1   TXLPolicyNameOrExpOrEmpty,
    tBgpPeerGroupPlcyImportPolicy2   TLPolicyNameOrExpOrEmpty,
    tBgpPeerGroupPlcyImportPolicy3   TLPolicyNameOrExpOrEmpty,
    tBgpPeerGroupPlcyImportPolicy4   TLPolicyNameOrExpOrEmpty,
    tBgpPeerGroupPlcyImportPolicy5   TLPolicyNameOrExpOrEmpty,
    tBgpPeerGroupPlcyImportPolicy6   TLPolicyNameOrExpOrEmpty,
    tBgpPeerGroupPlcyImportPolicy7   TLPolicyNameOrExpOrEmpty,
    tBgpPeerGroupPlcyImportPolicy8   TLPolicyNameOrExpOrEmpty,
    tBgpPeerGroupPlcyImportPolicy9   TLPolicyNameOrExpOrEmpty,
    tBgpPeerGroupPlcyImportPolicy10  TLPolicyNameOrExpOrEmpty,
    tBgpPeerGroupPlcyImportPolicy11  TLPolicyNameOrExpOrEmpty,
    tBgpPeerGroupPlcyImportPolicy12  TLPolicyNameOrExpOrEmpty,
    tBgpPeerGroupPlcyImportPolicy13  TLPolicyNameOrExpOrEmpty,
    tBgpPeerGroupPlcyImportPolicy14  TLPolicyNameOrExpOrEmpty,
    tBgpPeerGroupPlcyImportPolicy15  TLPolicyNameOrExpOrEmpty,
    tBgpPeerGroupPlcyExportPolicy1   TXLPolicyNameOrExpOrEmpty,
    tBgpPeerGroupPlcyExportPolicy2   TLPolicyNameOrExpOrEmpty,
    tBgpPeerGroupPlcyExportPolicy3   TLPolicyNameOrExpOrEmpty,
    tBgpPeerGroupPlcyExportPolicy4   TLPolicyNameOrExpOrEmpty,
    tBgpPeerGroupPlcyExportPolicy5   TLPolicyNameOrExpOrEmpty,
    tBgpPeerGroupPlcyExportPolicy6   TLPolicyNameOrExpOrEmpty,
    tBgpPeerGroupPlcyExportPolicy7   TLPolicyNameOrExpOrEmpty,
    tBgpPeerGroupPlcyExportPolicy8   TLPolicyNameOrExpOrEmpty,
    tBgpPeerGroupPlcyExportPolicy9   TLPolicyNameOrExpOrEmpty,
    tBgpPeerGroupPlcyExportPolicy10  TLPolicyNameOrExpOrEmpty,
    tBgpPeerGroupPlcyExportPolicy11  TLPolicyNameOrExpOrEmpty,
    tBgpPeerGroupPlcyExportPolicy12  TLPolicyNameOrExpOrEmpty,
    tBgpPeerGroupPlcyExportPolicy13  TLPolicyNameOrExpOrEmpty,
    tBgpPeerGroupPlcyExportPolicy14  TLPolicyNameOrExpOrEmpty,
    tBgpPeerGroupPlcyExportPolicy15  TLPolicyNameOrExpOrEmpty
}

tBgpPeerGroupPlcyImportPolicy1   OBJECT-TYPE
    SYNTAX      TXLPolicyNameOrExpOrEmpty
    MAX-ACCESS  read-create
    STATUS      current
    DESCRIPTION
        "The value of tBgpPeerGroupPlcyImportPolicy1 specifies the first import
         policy."
    DEFVAL      { ''H }
    ::= { tBgpPeerGroupPlcyEntry 1 }

tBgpPeerGroupPlcyImportPolicy2   OBJECT-TYPE
    SYNTAX      TLPolicyNameOrExpOrEmpty
    MAX-ACCESS  read-create
    STATUS      current
    DESCRIPTION
        "The value of tBgpPeerGroupPlcyImportPolicy2 specifies the second
         import policy."
    DEFVAL      { ''H }
    ::= { tBgpPeerGroupPlcyEntry 2 }

tBgpPeerGroupPlcyImportPolicy3   OBJECT-TYPE
    SYNTAX      TLPolicyNameOrExpOrEmpty
    MAX-ACCESS  read-create
    STATUS      current
    DESCRIPTION
        "The value of tBgpPeerGroupPlcyImportPolicy3 specifies the third import
         policy."
    DEFVAL      { ''H }
    ::= { tBgpPeerGroupPlcyEntry 3 }

tBgpPeerGroupPlcyImportPolicy4   OBJECT-TYPE
    SYNTAX      TLPolicyNameOrExpOrEmpty
    MAX-ACCESS  read-create
    STATUS      current
    DESCRIPTION
        "The value of tBgpPeerGroupPlcyImportPolicy4 specifies the fourth
         import policy."
    DEFVAL      { ''H }
    ::= { tBgpPeerGroupPlcyEntry 4 }

tBgpPeerGroupPlcyImportPolicy5   OBJECT-TYPE
    SYNTAX      TLPolicyNameOrExpOrEmpty
    MAX-ACCESS  read-create
    STATUS      current
    DESCRIPTION
        "The value of tBgpPeerGroupPlcyImportPolicy5 specifies the fifth import
         policy."
    DEFVAL      { ''H }
    ::= { tBgpPeerGroupPlcyEntry 5 }

tBgpPeerGroupPlcyImportPolicy6   OBJECT-TYPE
    SYNTAX      TLPolicyNameOrExpOrEmpty
    MAX-ACCESS  read-create
    STATUS      current
    DESCRIPTION
        "The value of tBgpPeerGroupPlcyImportPolicy6 specifies the sixth import
         policy."
    DEFVAL      { ''H }
    ::= { tBgpPeerGroupPlcyEntry 6 }

tBgpPeerGroupPlcyImportPolicy7   OBJECT-TYPE
    SYNTAX      TLPolicyNameOrExpOrEmpty
    MAX-ACCESS  read-create
    STATUS      current
    DESCRIPTION
        "The value of tBgpPeerGroupPlcyImportPolicy7 specifies the seventh
         import policy."
    DEFVAL      { ''H }
    ::= { tBgpPeerGroupPlcyEntry 7 }

tBgpPeerGroupPlcyImportPolicy8   OBJECT-TYPE
    SYNTAX      TLPolicyNameOrExpOrEmpty
    MAX-ACCESS  read-create
    STATUS      current
    DESCRIPTION
        "The value of tBgpPeerGroupPlcyImportPolicy8 specifies the eighth
         import policy."
    DEFVAL      { ''H }
    ::= { tBgpPeerGroupPlcyEntry 8 }

tBgpPeerGroupPlcyImportPolicy9   OBJECT-TYPE
    SYNTAX      TLPolicyNameOrExpOrEmpty
    MAX-ACCESS  read-create
    STATUS      current
    DESCRIPTION
        "The value of tBgpPeerGroupPlcyImportPolicy9 specifies the ninth import
         policy."
    DEFVAL      { ''H }
    ::= { tBgpPeerGroupPlcyEntry 9 }

tBgpPeerGroupPlcyImportPolicy10  OBJECT-TYPE
    SYNTAX      TLPolicyNameOrExpOrEmpty
    MAX-ACCESS  read-create
    STATUS      current
    DESCRIPTION
        "The value of tBgpPeerGroupPlcyImportPolicy10 specifies the tenth
         import policy."
    DEFVAL      { ''H }
    ::= { tBgpPeerGroupPlcyEntry 10 }

tBgpPeerGroupPlcyImportPolicy11  OBJECT-TYPE
    SYNTAX      TLPolicyNameOrExpOrEmpty
    MAX-ACCESS  read-create
    STATUS      current
    DESCRIPTION
        "The value of tBgpPeerGroupPlcyImportPolicy11 specifies the eleventh
         import policy."
    DEFVAL      { ''H }
    ::= { tBgpPeerGroupPlcyEntry 11 }

tBgpPeerGroupPlcyImportPolicy12  OBJECT-TYPE
    SYNTAX      TLPolicyNameOrExpOrEmpty
    MAX-ACCESS  read-create
    STATUS      current
    DESCRIPTION
        "The value of tBgpPeerGroupPlcyImportPolicy12 specifies the twelfth
         import policy."
    DEFVAL      { ''H }
    ::= { tBgpPeerGroupPlcyEntry 12 }

tBgpPeerGroupPlcyImportPolicy13  OBJECT-TYPE
    SYNTAX      TLPolicyNameOrExpOrEmpty
    MAX-ACCESS  read-create
    STATUS      current
    DESCRIPTION
        "The value of tBgpPeerGroupPlcyImportPolicy13 specifies the thirteenth
         import policy."
    DEFVAL      { ''H }
    ::= { tBgpPeerGroupPlcyEntry 13 }

tBgpPeerGroupPlcyImportPolicy14  OBJECT-TYPE
    SYNTAX      TLPolicyNameOrExpOrEmpty
    MAX-ACCESS  read-create
    STATUS      current
    DESCRIPTION
        "The value of tBgpPeerGroupPlcyImportPolicy14 specifies the fourteenth
         import policy."
    DEFVAL      { ''H }
    ::= { tBgpPeerGroupPlcyEntry 14 }

tBgpPeerGroupPlcyImportPolicy15  OBJECT-TYPE
    SYNTAX      TLPolicyNameOrExpOrEmpty
    MAX-ACCESS  read-create
    STATUS      current
    DESCRIPTION
        "The value of tBgpPeerGroupPlcyImportPolicy15 specifies the fifteenth
         import policy."
    DEFVAL      { ''H }
    ::= { tBgpPeerGroupPlcyEntry 15 }

tBgpPeerGroupPlcyExportPolicy1   OBJECT-TYPE
    SYNTAX      TXLPolicyNameOrExpOrEmpty
    MAX-ACCESS  read-create
    STATUS      current
    DESCRIPTION
        "The value of tBgpPeerGroupPlcyExportPolicy1 specifies the first export
         policy."
    DEFVAL      { ''H }
    ::= { tBgpPeerGroupPlcyEntry 16 }

tBgpPeerGroupPlcyExportPolicy2   OBJECT-TYPE
    SYNTAX      TLPolicyNameOrExpOrEmpty
    MAX-ACCESS  read-create
    STATUS      current
    DESCRIPTION
        "The value of tBgpPeerGroupPlcyExportPolicy2 specifies the second
         export policy."
    DEFVAL      { ''H }
    ::= { tBgpPeerGroupPlcyEntry 17 }

tBgpPeerGroupPlcyExportPolicy3   OBJECT-TYPE
    SYNTAX      TLPolicyNameOrExpOrEmpty
    MAX-ACCESS  read-create
    STATUS      current
    DESCRIPTION
        "The value of tBgpPeerGroupPlcyExportPolicy3 specifies the third export
         policy."
    DEFVAL      { ''H }
    ::= { tBgpPeerGroupPlcyEntry 18 }

tBgpPeerGroupPlcyExportPolicy4   OBJECT-TYPE
    SYNTAX      TLPolicyNameOrExpOrEmpty
    MAX-ACCESS  read-create
    STATUS      current
    DESCRIPTION
        "The value of tBgpPeerGroupPlcyExportPolicy4 specifies the fourth
         export policy."
    DEFVAL      { ''H }
    ::= { tBgpPeerGroupPlcyEntry 19 }

tBgpPeerGroupPlcyExportPolicy5   OBJECT-TYPE
    SYNTAX      TLPolicyNameOrExpOrEmpty
    MAX-ACCESS  read-create
    STATUS      current
    DESCRIPTION
        "The value of tBgpPeerGroupPlcyExportPolicy5 specifies the fifth export
         policy."
    DEFVAL      { ''H }
    ::= { tBgpPeerGroupPlcyEntry 20 }

tBgpPeerGroupPlcyExportPolicy6   OBJECT-TYPE
    SYNTAX      TLPolicyNameOrExpOrEmpty
    MAX-ACCESS  read-create
    STATUS      current
    DESCRIPTION
        "The value of tBgpPeerGroupPlcyExportPolicy6 specifies the sixth export
         policy."
    DEFVAL      { ''H }
    ::= { tBgpPeerGroupPlcyEntry 21 }

tBgpPeerGroupPlcyExportPolicy7   OBJECT-TYPE
    SYNTAX      TLPolicyNameOrExpOrEmpty
    MAX-ACCESS  read-create
    STATUS      current
    DESCRIPTION
        "The value of tBgpPeerGroupPlcyExportPolicy7 specifies the seventh
         export policy."
    DEFVAL      { ''H }
    ::= { tBgpPeerGroupPlcyEntry 22 }

tBgpPeerGroupPlcyExportPolicy8   OBJECT-TYPE
    SYNTAX      TLPolicyNameOrExpOrEmpty
    MAX-ACCESS  read-create
    STATUS      current
    DESCRIPTION
        "The value of tBgpPeerGroupPlcyExportPolicy8 specifies the eighth
         export policy."
    DEFVAL      { ''H }
    ::= { tBgpPeerGroupPlcyEntry 23 }

tBgpPeerGroupPlcyExportPolicy9   OBJECT-TYPE
    SYNTAX      TLPolicyNameOrExpOrEmpty
    MAX-ACCESS  read-create
    STATUS      current
    DESCRIPTION
        "The value of tBgpPeerGroupPlcyExportPolicy9 specifies the ninth export
         policy."
    DEFVAL      { ''H }
    ::= { tBgpPeerGroupPlcyEntry 24 }

tBgpPeerGroupPlcyExportPolicy10  OBJECT-TYPE
    SYNTAX      TLPolicyNameOrExpOrEmpty
    MAX-ACCESS  read-create
    STATUS      current
    DESCRIPTION
        "The value of tBgpPeerGroupPlcyExportPolicy10 specifies the tenth
         export policy."
    DEFVAL      { ''H }
    ::= { tBgpPeerGroupPlcyEntry 25 }

tBgpPeerGroupPlcyExportPolicy11  OBJECT-TYPE
    SYNTAX      TLPolicyNameOrExpOrEmpty
    MAX-ACCESS  read-create
    STATUS      current
    DESCRIPTION
        "The value of tBgpPeerGroupPlcyExportPolicy11 specifies the eleventh
         export policy."
    DEFVAL      { ''H }
    ::= { tBgpPeerGroupPlcyEntry 26 }

tBgpPeerGroupPlcyExportPolicy12  OBJECT-TYPE
    SYNTAX      TLPolicyNameOrExpOrEmpty
    MAX-ACCESS  read-create
    STATUS      current
    DESCRIPTION
        "The value of tBgpPeerGroupPlcyExportPolicy12 specifies the twelfth
         export policy."
    DEFVAL      { ''H }
    ::= { tBgpPeerGroupPlcyEntry 27 }

tBgpPeerGroupPlcyExportPolicy13  OBJECT-TYPE
    SYNTAX      TLPolicyNameOrExpOrEmpty
    MAX-ACCESS  read-create
    STATUS      current
    DESCRIPTION
        "The value of tBgpPeerGroupPlcyExportPolicy13 specifies the thirteenth
         export policy."
    DEFVAL      { ''H }
    ::= { tBgpPeerGroupPlcyEntry 28 }

tBgpPeerGroupPlcyExportPolicy14  OBJECT-TYPE
    SYNTAX      TLPolicyNameOrExpOrEmpty
    MAX-ACCESS  read-create
    STATUS      current
    DESCRIPTION
        "The value of tBgpPeerGroupPlcyExportPolicy14 specifies the fourteenth
         export policy."
    DEFVAL      { ''H }
    ::= { tBgpPeerGroupPlcyEntry 29 }

tBgpPeerGroupPlcyExportPolicy15  OBJECT-TYPE
    SYNTAX      TLPolicyNameOrExpOrEmpty
    MAX-ACCESS  read-create
    STATUS      current
    DESCRIPTION
        "The value of tBgpPeerGroupPlcyExportPolicy15 specifies the fifteenth
         export policy."
    DEFVAL      { ''H }
    ::= { tBgpPeerGroupPlcyEntry 30 }

tBgpPeerGroupPfxLmtTableLstChgd  OBJECT-TYPE
    SYNTAX      TimeStamp
    MAX-ACCESS  read-only
    STATUS      current
    DESCRIPTION
        "The value of tBgpPeerGroupPfxLmtTableLstChgd indicates the last
         timestamp when an entry in the tBgpPeerGroupPfxLmtTable was last
         changed."
    ::= { tBgpPeerGroupObjects 7 }

tBgpPeerGroupPfxLmtTable         OBJECT-TYPE
    SYNTAX      SEQUENCE OF TBgpPeerGroupPfxLmtEntry
    MAX-ACCESS  not-accessible
    STATUS      current
    DESCRIPTION
        "The tBgpPeerGroupPfxLmtTable is the list of configured prefix limits
         for different family types for configured BGP Peer Groups. The table
         entries are indexed by BGP instance, peer group name and family type."
    ::= { tBgpPeerGroupObjects 8 }

tBgpPeerGroupPfxLmtEntry         OBJECT-TYPE
    SYNTAX      TBgpPeerGroupPfxLmtEntry
    MAX-ACCESS  not-accessible
    STATUS      current
    DESCRIPTION
        "An entry (conceptual row) in the tBgpPeerGroupPfxLmtTable.

         An entry can be created using the row status object,
         tBgpPeerGroupPfxLmtRowStatus. When created, all objects are
         initialized to their default values.

         Before the peer entry can be used, tBgpPeerGroupPfxLmtRowStatus must
         be set to 'active(1)'. The peer entry can be removed by setting
         tBgpPeerGroupPfxLmtRowStatus to 'destroy(6)'."
    INDEX       {
        tBgpInstanceIndex,
        tBgpPeerGroupName,
        tBgpPeerGroupPfxLmtFamily
    }
    ::= { tBgpPeerGroupPfxLmtTable 1 }

TBgpPeerGroupPfxLmtEntry         ::= SEQUENCE
{
    tBgpPeerGroupPfxLmtFamily        TmnxIpFamilyIdentifier,
    tBgpPeerGroupPfxLmtLastChanged   TimeStamp,
    tBgpPeerGroupPfxLmtRowStatus     RowStatus,
    tBgpPeerGroupPfxLmtMaxPrefix     BgpPrefixLimit,
    tBgpPeerGroupPfxLmtLogOnly       TruthValue,
    tBgpPeerGroupPfxLmtThreshold     Unsigned32,
    tBgpPeerGroupPfxLmtIdleTimeOut   Integer32,
    tBgpPeerGroupPfxLmtPostImport    TruthValue,
    tBgpPeerGroupPfxLmtHoldExcess    Integer32
}

tBgpPeerGroupPfxLmtFamily        OBJECT-TYPE
    SYNTAX      TmnxIpFamilyIdentifier
    MAX-ACCESS  not-accessible
    STATUS      current
    DESCRIPTION
        "The value of tBgpPeerGroupPfxLmtFamily specifies the address family
         for which prefix-limit is configured."
    ::= { tBgpPeerGroupPfxLmtEntry 1 }

tBgpPeerGroupPfxLmtLastChanged   OBJECT-TYPE
    SYNTAX      TimeStamp
    MAX-ACCESS  read-only
    STATUS      current
    DESCRIPTION
        "The value tBgpPeerGroupPfxLmtLastChanged indicates when an entry in
         tBgpPeerGroupPfxLmtTable was last changed."
    ::= { tBgpPeerGroupPfxLmtEntry 2 }

tBgpPeerGroupPfxLmtRowStatus     OBJECT-TYPE
    SYNTAX      RowStatus
    MAX-ACCESS  read-create
    STATUS      current
    DESCRIPTION
        "The value of tBgpPeerGroupPfxLmtRowStatus specifies the row status for
         this BGP instance for the virtual router. It is used to create and
         delete row entries in this table."
    ::= { tBgpPeerGroupPfxLmtEntry 3 }

tBgpPeerGroupPfxLmtMaxPrefix     OBJECT-TYPE
    SYNTAX      BgpPrefixLimit
    UNITS       "number of routes"
    MAX-ACCESS  read-create
    STATUS      current
    DESCRIPTION
        "The value of tBgpPeerGroupPfxLmtMaxPrefix specifies the maximum number
         of routes that can be learned from this peer.

         A value of zero specifies there is no limit to the number of routes
         learned.

         The tBgpMaxNgPfxLmtThresholdReached notification is sent when the
         number of routes exceeds a percentage of this limit as specified by
         tBgpPeerGroupPfxLmtThreshold.

         When the number of routes exceeds this limit, then BGP peering will be
         disabled and the tBgpMaxNgPfxLmt notification will be sent."
    DEFVAL      { 0 }
    ::= { tBgpPeerGroupPfxLmtEntry 4 }

tBgpPeerGroupPfxLmtLogOnly       OBJECT-TYPE
    SYNTAX      TruthValue
    MAX-ACCESS  read-create
    STATUS      current
    DESCRIPTION
        "The value of tBgpPeerGroupPfxLmtLogOnly specifies whether BGP peering
         will be disabled when tBgpPeerGroupPfxLmtMaxPrefix is exceeded.

         When the value is set to 'true', BGP peering will be enabled.

         When the value is set to 'false', BGP peering will be disabled."
    DEFVAL      { false }
    ::= { tBgpPeerGroupPfxLmtEntry 5 }

tBgpPeerGroupPfxLmtThreshold     OBJECT-TYPE
    SYNTAX      Unsigned32 (1..100)
    UNITS       "percent"
    MAX-ACCESS  read-create
    STATUS      current
    DESCRIPTION
        "The value of tBgpPeerGroupPfxLmtThreshold specifies a percentage of
         tBgpPeerGroupPfxLmtMaxPrefix."
    DEFVAL      { 90 }
    ::= { tBgpPeerGroupPfxLmtEntry 6 }

tBgpPeerGroupPfxLmtIdleTimeOut   OBJECT-TYPE
    SYNTAX      Integer32 (0..1024)
    UNITS       "minutes"
    MAX-ACCESS  read-create
    STATUS      current
    DESCRIPTION
        "The value of tBgpPeerGroupPfxLmtIdleTimeOut specifies the idle time in
         minutes that the BGP peering remains disabled before attempting to
         automatically re-establish the connection with the peers in this BGP
         group after tBgpPeerGroupPfxLmtMaxPrefix limit is reached.

         The default value of tBgpPeerGroupPfxLmtIdleTimeOut is zero which
         means, no attempt will be made to re-establish the BGP peering with
         peers in this BGP group after tBgpPeerGroupPfxLmtMaxPrefix limit is
         reached.

         When the value of tBgpPeerGroupPfxLmtMaxPrefix is changed, the value
         of tBgpPeerGroupPfxLmtIdleTimeOut is reset to its default value.

         An 'inconsistentValue' error is returned if an attempt is made to set
         this object to a non-default value when the value of
         tBgpPeerGroupPfxLmtMaxPrefix is set to default value or the value of
         tBgpPeerGroupPfxLmtLogOnly is set to non-default value."
    DEFVAL      { 0 }
    ::= { tBgpPeerGroupPfxLmtEntry 7 }

tBgpPeerGroupPfxLmtPostImport    OBJECT-TYPE
    SYNTAX      TruthValue
    MAX-ACCESS  read-create
    STATUS      current
    DESCRIPTION
        "The value of tBgpPeerGroupPfxLmtPostImport specifies that a route
         rejected by a BGP import policy should not be counted against the
         configured tBgpPeerGroupPfxLmtMaxPrefix limit.

         When the value is set to 'true', it specifies that the limit should be
         enforced after import policies."
    DEFVAL      { false }
    ::= { tBgpPeerGroupPfxLmtEntry 8 }

tBgpPeerGroupPfxLmtHoldExcess    OBJECT-TYPE
    SYNTAX      Integer32 (-1 | 1..100)
    UNITS       "percent"
    MAX-ACCESS  read-create
    STATUS      current
    DESCRIPTION
        "The value of tBgpPeerGroupPfxLmtHoldExcess specifies a percentage of
         tBgpPeerGroupPfxLmtMaxPrefix.

         When the number of received routes reaches the limit (or a percentage
         of the limit), those  excess routes are retained in the BGP RIB-IN,
         but not installed to the route table/FIB.  Excess routes are not
         automatically installed when room becomes available due to route
         withdrawals  or policy rejections. A clear command must be issued to
         trigger re-evaluation. When the value is set to -1, the received
         routes would be handled by other desired behaviors other than holding
         excess routes"
    DEFVAL      { -1 }
    ::= { tBgpPeerGroupPfxLmtEntry 11 }

tBgpPGDynamicPeerPfxTableLstChgd OBJECT-TYPE
    SYNTAX      TimeStamp
    MAX-ACCESS  read-only
    STATUS      current
    DESCRIPTION
        "The value of tBgpPGDynamicPeerPfxTableLstChgd indicates the last
         timestamp when an entry in the tBgpPeerGroupDynamicPeerPfxTable was
         last changed."
    ::= { tBgpPeerGroupObjects 9 }

tBgpPeerGroupDynamicPeerPfxTable OBJECT-TYPE
    SYNTAX      SEQUENCE OF TBgpPeerGroupDynamicPeerPfxEntry
    MAX-ACCESS  not-accessible
    STATUS      current
    DESCRIPTION
        "The tBgpPeerGroupDynamicPeerPfxTable is the list of configured
         prefixes for dynamic peers configured under BGP Peer Groups. The table
         entries are indexed by BGP instance, prefix address and prefix mask."
    ::= { tBgpPeerGroupObjects 10 }

tBgpPeerGroupDynamicPeerPfxEntry OBJECT-TYPE
    SYNTAX      TBgpPeerGroupDynamicPeerPfxEntry
    MAX-ACCESS  not-accessible
    STATUS      current
    DESCRIPTION
        "An entry (conceptual row) in the tBgpPeerGroupDynamicPeerPfxTable.

         An entry can be created using the row status object,
         tBgpPGDynamicPeerPfxRowStatus. When created, all objects are
         initialized to their default values. Setting RowStatus to 'active'
         requires tBgpPGDynamicPeerPfxGroupName to have been assigned a valid
         value."
    INDEX       {
        tBgpInstanceIndex,
        tBgpPGDynamicPeerPrefixType,
        tBgpPGDynamicPeerPrefix,
        tBgpPGDynamicPeerPrefixLength
    }
    ::= { tBgpPeerGroupDynamicPeerPfxTable 1 }

TBgpPeerGroupDynamicPeerPfxEntry ::= SEQUENCE
{
    tBgpPGDynamicPeerPrefixType      InetAddressType,
    tBgpPGDynamicPeerPrefix          InetAddress,
    tBgpPGDynamicPeerPrefixLength    InetAddressPrefixLength,
    tBgpPGDynamicPeerPfxLastChanged  TimeStamp,
    tBgpPGDynamicPeerPfxRowStatus    RowStatus,
    tBgpPGDynamicPeerPfxGroupName    BgpPeerGroupName
}

tBgpPGDynamicPeerPrefixType      OBJECT-TYPE
    SYNTAX      InetAddressType
    MAX-ACCESS  not-accessible
    STATUS      current
    DESCRIPTION
        "The value of tBgpPGDynamicPeerPrefixType specifies the address type of
         tBgpPGDynamicPeerPrefix prefix."
    ::= { tBgpPeerGroupDynamicPeerPfxEntry 1 }

tBgpPGDynamicPeerPrefix          OBJECT-TYPE
    SYNTAX      InetAddress (SIZE (4|16|20))
    MAX-ACCESS  not-accessible
    STATUS      current
    DESCRIPTION
        "The value of tBgpPGDynamicPeerPrefix specifies the dynamic peer prefix
         for this group."
    ::= { tBgpPeerGroupDynamicPeerPfxEntry 2 }

tBgpPGDynamicPeerPrefixLength    OBJECT-TYPE
    SYNTAX      InetAddressPrefixLength (0..128)
    MAX-ACCESS  not-accessible
    STATUS      current
    DESCRIPTION
        "The value of tBgpPGDynamicPeerPrefixLength specifies the value of the
         prefix length for tBgpPGDynamicPeerPrefix"
    ::= { tBgpPeerGroupDynamicPeerPfxEntry 3 }

tBgpPGDynamicPeerPfxLastChanged  OBJECT-TYPE
    SYNTAX      TimeStamp
    MAX-ACCESS  read-only
    STATUS      current
    DESCRIPTION
        "The value of tBgpPGDynamicPeerPfxLastChanged indicates the sysUpTime
         when this row was last modified."
    ::= { tBgpPeerGroupDynamicPeerPfxEntry 4 }

tBgpPGDynamicPeerPfxRowStatus    OBJECT-TYPE
    SYNTAX      RowStatus
    MAX-ACCESS  read-create
    STATUS      current
    DESCRIPTION
        "The value of tBgpPGDynamicPeerPfxRowStatus specifies the row status
         for this dynamic peer entry for this group. It is used to create and
         delete row entries in this table."
    ::= { tBgpPeerGroupDynamicPeerPfxEntry 5 }

tBgpPGDynamicPeerPfxGroupName    OBJECT-TYPE
    SYNTAX      BgpPeerGroupName
    MAX-ACCESS  read-create
    STATUS      current
    DESCRIPTION
        "The value of tBgpPGDynamicPeerPfxGroupName specifies the group name to
         which this dynamic peer belongs to. The value
         tBgpPGDynamicPeerPfxGroupName needs to be set at row creation time."
    ::= { tBgpPeerGroupDynamicPeerPfxEntry 6 }

tBgpPGLLGRFamilyTblLstCh         OBJECT-TYPE
    SYNTAX      TimeStamp
    MAX-ACCESS  read-only
    STATUS      current
    DESCRIPTION
        "The value of tBgpPGLLGRFamilyTblLstCh indicates the timestamp when an
         entry in tBgpPGLLGRFamilyTable was last changed."
    ::= { tBgpPeerGroupObjects 11 }

tBgpPGLLGRFamilyTable            OBJECT-TYPE
    SYNTAX      SEQUENCE OF TBgpPGLLGRFamilyEntry
    MAX-ACCESS  not-accessible
    STATUS      current
    DESCRIPTION
        "The tBgpPGLLGRFamilyTable consists of information about the BGP LLGR
         Family specific parameters. The table entries are indexed by BGP
         instance, Peer Group name and LLGR AFI/SAFI."
    ::= { tBgpPeerGroupObjects 12 }

tBgpPGLLGRFamilyEntry            OBJECT-TYPE
    SYNTAX      TBgpPGLLGRFamilyEntry
    MAX-ACCESS  not-accessible
    STATUS      current
    DESCRIPTION
        "An entry (conceptual row) in the tBgpPGLLGRFamilyTable."
    INDEX       {
        tBgpInstanceIndex,
        tBgpPeerGroupName,
        tBgpPGLLGRFamily
    }
    ::= { tBgpPGLLGRFamilyTable 1 }

TBgpPGLLGRFamilyEntry            ::= SEQUENCE
{
    tBgpPGLLGRFamily                 TmnxIpFamilyIdentifier,
    tBgpPGLLGRFamilyLstCh            TimeStamp,
    tBgpPGLLGRFamilyRowStatus        RowStatus,
    tBgpPGLLGRFamilyAdvStaleTime     Unsigned32,
    tBgpPGLLGRFamilyOvrideStaleTm    Unsigned32
}

tBgpPGLLGRFamily                 OBJECT-TYPE
    SYNTAX      TmnxIpFamilyIdentifier
    MAX-ACCESS  not-accessible
    STATUS      current
    DESCRIPTION
        "The value of tBgpPGLLGRFamily specifies the particular AFI/SAFI that
         this configuration applies to."
    ::= { tBgpPGLLGRFamilyEntry 1 }

tBgpPGLLGRFamilyLstCh            OBJECT-TYPE
    SYNTAX      TimeStamp
    MAX-ACCESS  read-only
    STATUS      current
    DESCRIPTION
        "The value tBgpPGLLGRFamilyLstCh indicates when an entry in
         tBgpPGLLGRFamilyTable was last changed."
    ::= { tBgpPGLLGRFamilyEntry 2 }

tBgpPGLLGRFamilyRowStatus        OBJECT-TYPE
    SYNTAX      RowStatus
    MAX-ACCESS  read-create
    STATUS      current
    DESCRIPTION
        "RowStatus for the PG LLGR Family entry."
    ::= { tBgpPGLLGRFamilyEntry 3 }

tBgpPGLLGRFamilyAdvStaleTime     OBJECT-TYPE
    SYNTAX      Unsigned32 (0..16777215)
    MAX-ACCESS  read-create
    STATUS      current
    DESCRIPTION
        "The value of tBgpPGLLGRFamilyAdvStaleTime specifies the time for which
         the route can be used for this AFI/SAFI after the peer is
         disconnected."
    DEFVAL      { 86400 }
    ::= { tBgpPGLLGRFamilyEntry 4 }

tBgpPGLLGRFamilyOvrideStaleTm    OBJECT-TYPE
    SYNTAX      Unsigned32 (0..16777216)
    MAX-ACCESS  read-create
    STATUS      current
    DESCRIPTION
        "The value of tBgpPGLLGRFamilyOvrideStaleTm specifies the stale time
         for this particular AFI/SAFI when the system is in helper mode."
    DEFVAL      { 16777216 }
    ::= { tBgpPGLLGRFamilyEntry 5 }

tBgpPGParamsExtTblLstCh          OBJECT-TYPE
    SYNTAX      TimeStamp
    MAX-ACCESS  read-only
    STATUS      current
    DESCRIPTION
        "The value of tBgpPGParamsExtTblLstCh indicates the timestamp when an
         entry in tBgpPeerGroupParamsExtTable was last changed."
    ::= { tBgpPeerGroupObjects 13 }

tBgpPeerGroupParamsExtTable      OBJECT-TYPE
    SYNTAX      SEQUENCE OF TBgpPeerGroupParamsExtEntry
    MAX-ACCESS  not-accessible
    STATUS      current
    DESCRIPTION
        "Information about the attributes configured  for
         the BGP instance."
    ::= { tBgpPeerGroupObjects 14 }

tBgpPeerGroupParamsExtEntry      OBJECT-TYPE
    SYNTAX      TBgpPeerGroupParamsExtEntry
    MAX-ACCESS  not-accessible
    STATUS      current
    DESCRIPTION
        "An entry in the tBgpPeerGroupParamsExtTable. Each entry maintains the
         attributes configured for BGP instance."
    AUGMENTS    { tBgpPeerGroupEntry }
    ::= { tBgpPeerGroupParamsExtTable 1 }

TBgpPeerGroupParamsExtEntry      ::= SEQUENCE
{
    tBgpPGParamsExtInheritanceHi     TmnxHigh32,
    tBgpPGParamsExtInheritanceLo     TmnxLow32,
    tBgpPGLinkAcceptEbgp             TmnxIpFamily,
    tBgpPGLinkSendEbgp               TmnxIpFamily,
    tBgpPGLinkAggPaths               TmnxIpFamily,
    tBgpPGLoopDetectThreshold        Unsigned32,
    tBgpPGSendExportPolicy           TLPolicyNameOrExpOrEmpty,
    tBgpPGEbgpPreference             TmnxBgpPreference,
    tBgpPGIbgpPreference             TmnxBgpPreference,
    tBgpPGEbgpLabelPreference        TmnxBgpPreference,
    tBgpPGIbgpLabelPreference        TmnxBgpPreference,
    tBgpPGEBGPRejWithoutPlcyImpt     TruthValue,
    tBgpPGEBGPRejWithoutPlcyExpt     TruthValue,
    tBgpPGMultipathEligible          TruthValue,
    tBgpPGRemovePrivateReplaceAs     TruthValue,
    tBgpPGBlockPrefixSID             TruthValue,
    tBgpPGDefOriginate               TmnxIpFamily,
    tBgpPGTcpMss                     Unsigned32,
    tBgpPGSelLabelIpv4Inst           TruthValue,
    tBgpPGEgressEng                  TruthValue,
    tBgpPGEgressEngShutdown          TmnxAdminState,
    tBgpPGSegmentRoutingV6           TruthValue,
    tBgpPGSrv6RouteAdvertisement     TruthValue,
    tBgpPGSrv6DropRoutes             TruthValue,
    tBgpPGEgressPeerEngLabelUnicast  TruthValue,
    tBgpPGEvpnLinkBWAddToRcvdBgp     Integer32,
    tBgpPGBfdStrictAdvertise         TruthValue,
    tBgpPGBfdStrictNhReach           TruthValue,
    tBgpPGBfdStrictHoldTime          Unsigned32
}

tBgpPGParamsExtInheritanceHi     OBJECT-TYPE
    SYNTAX      TmnxHigh32 (0..4294967295)
    MAX-ACCESS  read-create
    STATUS      current
    DESCRIPTION
        "The value of tBgpPGParamsExtInheritanceHi specifies the upper 32 bits
         of inheritance object. The object specifies if the peer entry in this
         row, should inherit the operational value of an object, or use the
         administratively set value.

         This object is a bit-mask, with the following positions:


         When the bit for an object is set to one, then the object's
         administrative and operational value are whatever the DEFVAL or most
         recently SET value is.

         When the bit for an object is set to zero, then the object's
         administrative and operational value are inherited from the
         corresponding object in tBgpInstanceTable.

         By default all of these attributes should be inherited from the
         tBgpInstanceTable."
    DEFVAL      { 0 }
    ::= { tBgpPeerGroupParamsExtEntry 1 }

tBgpPGParamsExtInheritanceLo     OBJECT-TYPE
    SYNTAX      TmnxLow32 (0..4294967295)
    MAX-ACCESS  read-create
    STATUS      current
    DESCRIPTION
        "The value of tBgpPGParamsExtInheritanceLo specifies the lower  32 bits
         of the inheritance object. The object specifies if the peer entry in
         this row, should inherit the operational value of an object, or use
         the administratively set value.

         This object is a bit-mask, with the following positions:
         tBgpPGParamsExtInheritanceHi        0x00000001
         tBgpPGParamsExtInheritanceLo        0x00000002
         tBgpPGLinkAcceptEbgp                0x00000004
         tBgpPGLinkSendEbgp                  0x00000008
         tBgpPGLinkAggPaths                  0x00000010
         tBgpPGLoopDetectThreshold           0x00000020
         tBgpPGSendExportPolicy              0x00000040
         tBgpPGEbgpPreference                0x00000080
         tBgpPGIbgpPreference                0x00000100
         tBgpPGEbgpLabelPreference           0x00000200
         tBgpPGIbgpLabelPreference           0x00000400
         tBgpPGEBGPRejWithoutPlcyImpt        0x00000800
         tBgpPGEBGPRejWithoutPlcyExpt        0x00001000
         tBgpPGMultipathEligible             0x00002000
         tBgpPGRemovePrivateReplaceAs        0x00004000
         tBgpPGBlockPrefixSID                0x00008000
         tBgpPGDefOriginate                  0x00010000
         tBgpPGTcpMss                        0x00020000
         tBgpPGSelLabelIpv4Inst              0x00040000
         tBgpPGEgressEng                     0x00080000
         reserved        0x00100000
         reserved        0x00200000
         reserved        0x00400000
         reserved        0x00800000
         reserved        0x01000000
         reserved        0x02000000
         reserved        0x04000000

         tBgpPGBfdStrictAdvertise           0x08000000
         tBgpPGBfdStrictNhReach             0x10000000

         reserved        0x20000000
         reserved        0x40000000
         reserved        0x80000000

         When the bit for an object is set to one, then the object's
         administrative and operational value are whatever the DEFVAL or most
         recently SET value is.

         When the bit for an object is set to zero, then the object's
         administrative and operational value are inherited from the
         corresponding object in tBgpInstanceTable.

         The bits marked as 'reserved' correspond to attributes that do  not
         have inheritance but the bits are reserved.

         By default all of these attributes should be inherited from the
         tBgpInstanceTable."
    DEFVAL      { 0 }
    ::= { tBgpPeerGroupParamsExtEntry 2 }

tBgpPGLinkAcceptEbgp             OBJECT-TYPE
    SYNTAX      TmnxIpFamily
    MAX-ACCESS  read-create
    STATUS      current
    DESCRIPTION
        "The value of tBgpPGLinkAcceptEbgp specifies the address families of
         the routes received from a single-hop EBGP neighbor, for which a Link
         Bandwidth Extended Community with static AS and bandwidth values is
         allowed."
    DEFVAL      { {} }
    ::= { tBgpPeerGroupParamsExtEntry 3 }

tBgpPGLinkSendEbgp               OBJECT-TYPE
    SYNTAX      TmnxIpFamily
    MAX-ACCESS  read-create
    STATUS      current
    DESCRIPTION
        "The value of tBgpPGLinkSendEbgp specifies the address families of the
         routes sent to a single-hop EBGP neighbor, for which a Link Bandwidth
         Extended Community with static AS and bandwidth values is allowed."
    DEFVAL      { {} }
    ::= { tBgpPeerGroupParamsExtEntry 4 }

tBgpPGLinkAggPaths               OBJECT-TYPE
    SYNTAX      TmnxIpFamily
    MAX-ACCESS  read-create
    STATUS      current
    DESCRIPTION
        "The value of tBgpPGLinkAggPaths specifies the families of the  routes
         for which aggregate bandwidth is supported  for a re-advertising
         router."
    DEFVAL      { {} }
    ::= { tBgpPeerGroupParamsExtEntry 5 }

tBgpPGLoopDetectThreshold        OBJECT-TYPE
    SYNTAX      Unsigned32 (0..15)
    MAX-ACCESS  read-create
    STATUS      current
    DESCRIPTION
        "The value of tBgpPGLoopDetectThreshold specifies the occurrence of the
         global ASN when exceeded triggers the loop-detect behavior."
    DEFVAL      { 0 }
    ::= { tBgpPeerGroupParamsExtEntry 6 }

tBgpPGSendExportPolicy           OBJECT-TYPE
    SYNTAX      TLPolicyNameOrExpOrEmpty
    MAX-ACCESS  read-create
    STATUS      current
    DESCRIPTION
        "The value of tBgpPGSendExportPolicy specifies the send default export
         policy."
    DEFVAL      { "" }
    ::= { tBgpPeerGroupParamsExtEntry 7 }

tBgpPGEbgpPreference             OBJECT-TYPE
    SYNTAX      TmnxBgpPreference (0..255)
    MAX-ACCESS  read-create
    STATUS      current
    DESCRIPTION
        "The value of tBgpPGEbgpPreference specifies the route preference for
         ebgp routes."
    DEFVAL      { 0 }
    ::= { tBgpPeerGroupParamsExtEntry 8 }

tBgpPGIbgpPreference             OBJECT-TYPE
    SYNTAX      TmnxBgpPreference (0..255)
    MAX-ACCESS  read-create
    STATUS      current
    DESCRIPTION
        "The value of tBgpPGIbgpPreference specifies the route preference for
         ibgp routes."
    DEFVAL      { 0 }
    ::= { tBgpPeerGroupParamsExtEntry 9 }

tBgpPGEbgpLabelPreference        OBJECT-TYPE
    SYNTAX      TmnxBgpPreference (0..255)
    MAX-ACCESS  read-create
    STATUS      current
    DESCRIPTION
        "The value of tBgpPGEbgpLabelPreference specifies the route preference
         for label-IPv4 and label-IPv6 ebgp routes."
    DEFVAL      { 0 }
    ::= { tBgpPeerGroupParamsExtEntry 10 }

tBgpPGIbgpLabelPreference        OBJECT-TYPE
    SYNTAX      TmnxBgpPreference (0..255)
    MAX-ACCESS  read-create
    STATUS      current
    DESCRIPTION
        "The value of tBgpPGIbgpLabelPreference specifies the route preference
         for label-IPv4 and label-IPv6 ibgp routes."
    DEFVAL      { 0 }
    ::= { tBgpPeerGroupParamsExtEntry 11 }

tBgpPGEBGPRejWithoutPlcyImpt     OBJECT-TYPE
    SYNTAX      TruthValue
    MAX-ACCESS  read-create
    STATUS      current
    DESCRIPTION
        "The value of tBgpPGEBGPRejWithoutPlcyImpt enables or disables if
         policies can be imported."
    DEFVAL      { false }
    ::= { tBgpPeerGroupParamsExtEntry 12 }

tBgpPGEBGPRejWithoutPlcyExpt     OBJECT-TYPE
    SYNTAX      TruthValue
    MAX-ACCESS  read-create
    STATUS      current
    DESCRIPTION
        "The value of tBgpPGEBGPRejWithoutPlcyExpt enables or disables if
         policies can be imported."
    DEFVAL      { false }
    ::= { tBgpPeerGroupParamsExtEntry 13 }

tBgpPGMultipathEligible          OBJECT-TYPE
    SYNTAX      TruthValue
    MAX-ACCESS  read-create
    STATUS      current
    DESCRIPTION
        "The value of tBgpPGMultipathEligible specifies whether this group is
         multi-path eligible."
    DEFVAL      { false }
    ::= { tBgpPeerGroupParamsExtEntry 14 }

tBgpPGRemovePrivateReplaceAs     OBJECT-TYPE
    SYNTAX      TruthValue
    MAX-ACCESS  read-create
    STATUS      current
    DESCRIPTION
        "The value of tBgpPGRemovePrivateReplaceAs specifies whether or not to
         replace the private autonomous system number (ASN) in AS-Path, if the
         AS-Path contains the ASN of the external BGP (eBGP) neighbor on this
         BGP peer group."
    DEFVAL      { false }
    ::= { tBgpPeerGroupParamsExtEntry 15 }

tBgpPGBlockPrefixSID             OBJECT-TYPE
    SYNTAX      TruthValue
    MAX-ACCESS  read-create
    STATUS      current
    DESCRIPTION
        "The value of tBgpPGBlockPrefixSID enables or disables sending of the
         prefix SID attribute."
    DEFVAL      { false }
    ::= { tBgpPeerGroupParamsExtEntry 16 }

tBgpPGDefOriginate               OBJECT-TYPE
    SYNTAX      TmnxIpFamily
    MAX-ACCESS  read-create
    STATUS      current
    DESCRIPTION
        "The value of tBgpPGDefOriginate specifies the types of AFI/SAFI for
         which SROS BGP will originate default route independent of the RTM
         default route."
    ::= { tBgpPeerGroupParamsExtEntry 17 }

tBgpPGTcpMss                     OBJECT-TYPE
    SYNTAX      Unsigned32 (0 | 384..9746)
    MAX-ACCESS  read-create
    STATUS      current
    DESCRIPTION
        "The value of tBgpPGTcpMss specifies the TCP maximum segment size(MSS).
         When the value of tBgpPGTcpMss is set to 0, the command removes the
         static value and allows the TCP MSS value to be calculated based on
         the IP MTU value."
    DEFVAL      { 0 }
    ::= { tBgpPeerGroupParamsExtEntry 18 }

tBgpPGSelLabelIpv4Inst           OBJECT-TYPE
    SYNTAX      TruthValue
    MAX-ACCESS  read-create
    STATUS      current
    DESCRIPTION
        "The value of tBgpPGSelLabelIpv4Inst specifies whether to
         enable/disable selective download of label-ipv4 routes"
    DEFVAL      { false }
    ::= { tBgpPeerGroupParamsExtEntry 19 }

tBgpPGEgressEng                  OBJECT-TYPE
    SYNTAX      TruthValue
    MAX-ACCESS  read-create
    STATUS      current
    DESCRIPTION
        "The value of tBgpPGEgressEng specifies whether to enable/disable
         egress peer engineering"
    DEFVAL      { false }
    ::= { tBgpPeerGroupParamsExtEntry 20 }

tBgpPGEgressEngShutdown          OBJECT-TYPE
    SYNTAX      TmnxAdminState
    MAX-ACCESS  read-create
    STATUS      current
    DESCRIPTION
        "The value of the object tBgpPGEgressEngShutdown specifies the desired
         administrative state of Egress Engineering for this BGP group."
    DEFVAL      { outOfService }
    ::= { tBgpPeerGroupParamsExtEntry 21 }

tBgpPGSegmentRoutingV6           OBJECT-TYPE
    SYNTAX      TruthValue
    MAX-ACCESS  read-create
    STATUS      current
    DESCRIPTION
        "The value of tBgpPGSegmentRoutingV6 specifies whether or not segment
         routing V6 capabilities are enabled on this group of BGP.

         When the value is set to 'false' segment routing V6 is disabled and
         any previous configuration of other segment routing parameters  is
         removed."
    DEFVAL      { false }
    ::= { tBgpPeerGroupParamsExtEntry 23 }

tBgpPGSrv6RouteAdvertisement     OBJECT-TYPE
    SYNTAX      TruthValue
    MAX-ACCESS  read-create
    STATUS      current
    DESCRIPTION
        "The value of tBgpPGSrv6RouteAdvertisement specifies whether or not
         segment routing V6 capabilities  for route advertisement
         are enabled on this group of BGP."
    DEFVAL      { false }
    ::= { tBgpPeerGroupParamsExtEntry 24 }

tBgpPGSrv6DropRoutes             OBJECT-TYPE
    SYNTAX      TruthValue
    MAX-ACCESS  read-create
    STATUS      current
    DESCRIPTION
        "The value of tBgpPGSrv6DropRoutes specifies whether or not to drop
         routes with srv6 tlvs for this group of BGP."
    DEFVAL      { false }
    ::= { tBgpPeerGroupParamsExtEntry 25 }

tBgpPGEgressPeerEngLabelUnicast  OBJECT-TYPE
    SYNTAX      TruthValue
    MAX-ACCESS  read-create
    STATUS      current
    DESCRIPTION
        "The value of tBgpPGEgressPeerEngLabelUnicast specifies whether to
         originate label unicast route on this group of BGP."
    DEFVAL      { false }
    ::= { tBgpPeerGroupParamsExtEntry 26 }

tBgpPGEvpnLinkBWAddToRcvdBgp     OBJECT-TYPE
    SYNTAX      Integer32 (-1 | 1..128)
    MAX-ACCESS  read-create
    STATUS      current
    DESCRIPTION
        "The value of tBgpPGEvpnLinkBWAddToRcvdBgp specifies whether a weight
         is internally added to the received PE-CE BGP routes in the VPRN and
         what  that weight is on this group of BGP.

         For the purpose of unequal ECMP, if EVPN-IFL and BGP PE-CE routes are
         combined into the same ECMP set and the value is in the range of
         [1..128],  the configured weight is added to all BGP PE-CE routes.
         When the value is  set to -1, ECMP set resulting from combining
         EVPN-IFL and BGP PE-CE route  will fallback to unweighted ECMP"
    DEFVAL      { -1 }
    ::= { tBgpPeerGroupParamsExtEntry 27 }

tBgpPGBfdStrictAdvertise         OBJECT-TYPE
    SYNTAX      TruthValue
    MAX-ACCESS  read-create
    STATUS      current
    DESCRIPTION
        "The value of tBgpPGBfdStrictAdvertise specifies whether strict
         Bi-directional Forwarding Detection will be advertised by this router.

         When the value is 'true', strict BFD mode capability is announced by
         this router"
    DEFVAL      { false }
    ::= { tBgpPeerGroupParamsExtEntry 28 }

tBgpPGBfdStrictNhReach           OBJECT-TYPE
    SYNTAX      TruthValue
    MAX-ACCESS  read-create
    STATUS      current
    DESCRIPTION
        "The value of tBgpPGBfdStrictNhReach specifies whether strict BFD mode
         will be used for next-hop reachability.

         When the value is 'true', the strict BFD state will be applied to the
         BGP next-hop"
    DEFVAL      { false }
    ::= { tBgpPeerGroupParamsExtEntry 29 }

tBgpPGBfdStrictHoldTime          OBJECT-TYPE
    SYNTAX      Unsigned32 (1..65535)
    MAX-ACCESS  read-create
    STATUS      current
    DESCRIPTION
        "The value of tBgpPGBfdStrictHoldTime specifies the BGP session hold
         time when the strict mode BFD session is not successfully established.

         When the value is not '0' the BGP session will be bounced after the
         configured time"
    DEFVAL      { 30 }
    ::= { tBgpPeerGroupParamsExtEntry 30 }

tBgpPeerGrpDynNbrAsRngTblLstChg  OBJECT-TYPE
    SYNTAX      TimeStamp
    MAX-ACCESS  read-only
    STATUS      current
    DESCRIPTION
        "The tBgpPeerGrpDynNbrAsRngTblLstChg indicates the last timestamp when
         an entry in the tBgpPeerGroupDynNbrAsRangeTable was last changed."
    ::= { tBgpPeerGroupObjects 15 }

tBgpPeerGroupDynNbrAsRangeTable  OBJECT-TYPE
    SYNTAX      SEQUENCE OF TBgpPeerGroupDynNbrAsRangeEntry
    MAX-ACCESS  not-accessible
    STATUS      current
    DESCRIPTION
        "The tBgpPeerGroupDynNbrAsRangeTable contains BGP peering
         dynamic-neighbor AS ranges."
    ::= { tBgpPeerGroupObjects 16 }

tBgpPeerGroupDynNbrAsRangeEntry  OBJECT-TYPE
    SYNTAX      TBgpPeerGroupDynNbrAsRangeEntry
    MAX-ACCESS  not-accessible
    STATUS      current
    DESCRIPTION
        "An entry (conceptual row) in the tBgpPeerGroupDynNbrAsRangeTable."
    INDEX       {
        tBgpInstanceIndex,
        tBgpPGDynamicPeerPrefixType,
        tBgpPGDynamicPeerPrefix,
        tBgpPGDynamicPeerPrefixLength,
        tBgpPeerGroupDynNbrAsRangeIndex
    }
    ::= { tBgpPeerGroupDynNbrAsRangeTable 1 }

TBgpPeerGroupDynNbrAsRangeEntry  ::= SEQUENCE
{
    tBgpPeerGroupDynNbrAsRangeIndex  Integer32,
    tBgpPeerGroupDynNbrAsRangeChg    TimeStamp,
    tBgpPeerGroupDynNbrAsRangeMin    Unsigned32,
    tBgpPeerGroupDynNbrAsRangeMax    Unsigned32
}

tBgpPeerGroupDynNbrAsRangeIndex  OBJECT-TYPE
    SYNTAX      Integer32 (1..32)
    MAX-ACCESS  not-accessible
    STATUS      current
    DESCRIPTION
        "The tBgpPeerGroupDynNbrAsRangeIndex indicates index used to store this
         range."
    ::= { tBgpPeerGroupDynNbrAsRangeEntry 1 }

tBgpPeerGroupDynNbrAsRangeChg    OBJECT-TYPE
    SYNTAX      TimeStamp
    MAX-ACCESS  read-only
    STATUS      current
    DESCRIPTION
        "The tBgpPeerGroupDynNbrAsRangeChg indicates when this entry was last
         changed."
    ::= { tBgpPeerGroupDynNbrAsRangeEntry 2 }

tBgpPeerGroupDynNbrAsRangeMin    OBJECT-TYPE
    SYNTAX      Unsigned32
    MAX-ACCESS  read-create
    STATUS      current
    DESCRIPTION
        "The tBgpPeerGroupDynNbrAsRangeMin specifies the minimum value of AS
         range."
    DEFVAL      { 0 }
    ::= { tBgpPeerGroupDynNbrAsRangeEntry 3 }

tBgpPeerGroupDynNbrAsRangeMax    OBJECT-TYPE
    SYNTAX      Unsigned32
    MAX-ACCESS  read-create
    STATUS      current
    DESCRIPTION
        "The tBgpPeerGroupDynNbrAsRangeMax specifies the maximum value of AS
         range."
    DEFVAL      { 0 }
    ::= { tBgpPeerGroupDynNbrAsRangeEntry 4 }

tBgpPGSrv6TblLstCh               OBJECT-TYPE
    SYNTAX      TimeStamp
    MAX-ACCESS  read-only
    STATUS      current
    DESCRIPTION
        "The value of tBgpPGSrv6TblLstCh indicates the last timestamp when an
         entry in the tBgpPGSrv6Table was last changed."
    ::= { tBgpPeerGroupObjects 29 }

tBgpPGSrv6Table                  OBJECT-TYPE
    SYNTAX      SEQUENCE OF TBgpPGSrv6Entry
    MAX-ACCESS  not-accessible
    STATUS      current
    DESCRIPTION
        "The tBgpPGSrv6Table is the list of configured objects  for different
         family types of segment-routing-v6.

         The table entries are indexed by BGP instance group name  and family
         type."
    ::= { tBgpPeerGroupObjects 30 }

tBgpPGSrv6Entry                  OBJECT-TYPE
    SYNTAX      TBgpPGSrv6Entry
    MAX-ACCESS  not-accessible
    STATUS      current
    DESCRIPTION
        "An entry (conceptual row) in the tBgpPGSrv6Table. When created, all
         objects are initialized to their default values."
    INDEX       {
        tBgpInstanceIndex,
        tBgpPeerGroupName,
        tBgpPGSrv6Family
    }
    ::= { tBgpPGSrv6Table 1 }

TBgpPGSrv6Entry                  ::= SEQUENCE
{
    tBgpPGSrv6Family                 TmnxIpFamilyIdentifier,
    tBgpPGSrv6RowStatus              RowStatus,
    tBgpPGSrv6LstCh                  TimeStamp,
    tBgpPGSrv6StripTlv               TruthValue
}

tBgpPGSrv6Family                 OBJECT-TYPE
    SYNTAX      TmnxIpFamilyIdentifier
    MAX-ACCESS  not-accessible
    STATUS      current
    DESCRIPTION
        "The value of tBgpPGSrv6Family specifies the address family for which
         the srv6 selection applies."
    ::= { tBgpPGSrv6Entry 1 }

tBgpPGSrv6RowStatus              OBJECT-TYPE
    SYNTAX      RowStatus
    MAX-ACCESS  read-create
    STATUS      current
    DESCRIPTION
        "The value of tBgpPGSrv6RowStatus specifies the row status for this
         table entry. It is used to create and delete row entries in this
         table."
    ::= { tBgpPGSrv6Entry 2 }

tBgpPGSrv6LstCh                  OBJECT-TYPE
    SYNTAX      TimeStamp
    MAX-ACCESS  read-only
    STATUS      current
    DESCRIPTION
        "The value tBgpPGSrv6LstCh indicates when an entry in tBgpPGSrv6Table
         was last changed."
    ::= { tBgpPGSrv6Entry 3 }

tBgpPGSrv6StripTlv               OBJECT-TYPE
    SYNTAX      TruthValue
    MAX-ACCESS  read-create
    STATUS      current
    DESCRIPTION
        "The value of tBgpPGSrv6StripTlv specifies the Srv6 TLVs need to be
         stripped  from outbound routes."
    DEFVAL      { false }
    ::= { tBgpPGSrv6Entry 4 }

tBgpPeerGroupAddPathTblLstCh     OBJECT-TYPE
    SYNTAX      TimeStamp
    MAX-ACCESS  read-only
    STATUS      current
    DESCRIPTION
        "The value of tBgpPeerGroupAddPathTblLstCh indicates the timestamp when
         an entry in the tBgpPeerGroupAddPathTable was last changed."
    ::= { tBgpPeerGroupObjects 31 }

tBgpPeerGroupAddPathTable        OBJECT-TYPE
    SYNTAX      SEQUENCE OF TBgpPeerGroupAddPathEntry
    MAX-ACCESS  not-accessible
    STATUS      current
    DESCRIPTION
        "The tBgpPeerGroupAddPathTable consists of information about the BGP
         Add Path parameters.

         The table entries are indexed by BGP instance and peer group name."
    ::= { tBgpPeerGroupObjects 32 }

tBgpPeerGroupAddPathEntry        OBJECT-TYPE
    SYNTAX      TBgpPeerGroupAddPathEntry
    MAX-ACCESS  not-accessible
    STATUS      current
    DESCRIPTION
        "An entry (conceptual row) in the tBgpPeerGroupAddPathTable.

         An entry can be created using the row status object,
         tBgpPGAddPathRowStatus. When created, all objects are initialized to
         their default values."
    INDEX       {
        tBgpInstanceIndex,
        tBgpPeerGroupName
    }
    ::= { tBgpPeerGroupAddPathTable 1 }

TBgpPeerGroupAddPathEntry        ::= SEQUENCE
{
    tBgpPGAddPathInheritance         TruthValue,
    tBgpPGAddPathRowStatus           RowStatus,
    tBgpPeerGroupAddPathLstCh        TimeStamp,
    tBgpPGAddPathRecv                TmnxAddPathAddressFamily,
    tBgpPGAddPathIpv4Limit           TmnxAddPathSendLimit,
    tBgpPGAddPathVpnIpv4Limit        TmnxAddPathSendLimit,
    tBgpPGAddPathIpv6Limit           TmnxAddPathSendLimit,
    tBgpPGAddPathVpnIpv6Limit        TmnxAddPathSendLimit,
    tBgpPGAddPathLblIpv4Limit        TmnxAddPathSendLimit,
    tBgpPGAddPathLblIpv6Limit        TmnxAddPathSendLimit,
    tBgpPGAddPathMvpnIpv4Limit       Integer32,
    tBgpPGAddPathMvpnIpv6Limit       Integer32,
    tBgpPGAddPathMcastVpnV4Limit     Integer32,
    tBgpPGAddPathMcastVpnV6Limit     Integer32,
    tBgpPGAddPathEvpnLimit           TmnxAddPathSendLimit
}

tBgpPGAddPathInheritance         OBJECT-TYPE
    SYNTAX      TruthValue
    MAX-ACCESS  read-only
    STATUS      current
    DESCRIPTION
        "The value of tBgpPGAddPathInheritance specifies if the group entry in
         this row, should inherit the operational value of an object, or use
         the administratively set value.

         When the value is 'false', then the object's administrative and
         operational value are whatever the DEFVAL or most recently SET value
         is.

         When the value is 'true', then the object's administrative and
         operational value are inherited from the corresponding object in
         tBgpPeerGroupAddPathTable."
    DEFVAL      { true }
    ::= { tBgpPeerGroupAddPathEntry 1 }

tBgpPGAddPathRowStatus           OBJECT-TYPE
    SYNTAX      RowStatus
    MAX-ACCESS  read-create
    STATUS      current
    DESCRIPTION
        "Row status of this BGP PG add-paths entry. A row cannot be created in
         this table if the tBgpInstanceIndex entry does not exist in the
         tBgpPeerGroupAddPathTable."
    ::= { tBgpPeerGroupAddPathEntry 2 }

tBgpPeerGroupAddPathLstCh        OBJECT-TYPE
    SYNTAX      TimeStamp
    MAX-ACCESS  read-only
    STATUS      current
    DESCRIPTION
        "The value tBgpPeerGroupAddPathLstCh indicates when an entry in
         tBgpPeerGroupAddPathTable was last changed."
    ::= { tBgpPeerGroupAddPathEntry 3 }

tBgpPGAddPathRecv                OBJECT-TYPE
    SYNTAX      TmnxAddPathAddressFamily
    MAX-ACCESS  read-create
    STATUS      current
    DESCRIPTION
        "The value of tBgpPGAddPathRecv specifies the address families which
         are enabled to receive BGP ADD-PATH on this peer group.

         ADD-PATH allows a BGP router to receive multiple distinct paths for
         the same prefix/NLRI (Network Layer Reachability Information)."
    DEFVAL      { {none} }
    ::= { tBgpPeerGroupAddPathEntry 4 }

tBgpPGAddPathIpv4Limit           OBJECT-TYPE
    SYNTAX      TmnxAddPathSendLimit
    MAX-ACCESS  read-create
    STATUS      current
    DESCRIPTION
        "The value of tBgpPGAddPathIpv4Limit specifies the maximum number of
         paths per IPv4 prefix that can be advertised to ADD-PATH peers on this
         peer group.

         An 'inconsistentValue' error is returned if an attempt is made to set
         this object to a value greater than tBgpInstanceMultipathBgp."
    DEFVAL      { 0 }
    ::= { tBgpPeerGroupAddPathEntry 5 }

tBgpPGAddPathVpnIpv4Limit        OBJECT-TYPE
    SYNTAX      TmnxAddPathSendLimit
    MAX-ACCESS  read-create
    STATUS      current
    DESCRIPTION
        "The value of tBgpPGAddPathVpnIpv4Limit specifies the maximum number of
         paths per VPN IPv4 prefix that can be advertised to ADD-PATH peers on
         this peer group.

         An 'inconsistentValue' error is returned if an attempt is made to set
         this object to a value greater than tBgpInstanceMultipathBgp."
    DEFVAL      { 0 }
    ::= { tBgpPeerGroupAddPathEntry 6 }

tBgpPGAddPathIpv6Limit           OBJECT-TYPE
    SYNTAX      TmnxAddPathSendLimit
    MAX-ACCESS  read-create
    STATUS      current
    DESCRIPTION
        "The value of tBgpPGAddPathIpv6Limit specifies the maximum number of
         paths per IPv6 prefix that can be advertised to ADD-PATH peers on this
         peer group.

         An 'inconsistentValue' error is returned if an attempt is made to set
         this object to a value greater than tBgpInstanceMultipathBgp."
    DEFVAL      { 0 }
    ::= { tBgpPeerGroupAddPathEntry 7 }

tBgpPGAddPathVpnIpv6Limit        OBJECT-TYPE
    SYNTAX      TmnxAddPathSendLimit
    MAX-ACCESS  read-create
    STATUS      current
    DESCRIPTION
        "The value of tBgpPGAddPathVpnIpv6Limit specifies the maximum number of
         paths per VPN IPv6 prefix that can be advertised to ADD-PATH peers on
         this peer group.

         An 'inconsistentValue' error is returned if an attempt is made to set
         this object to a value greater than tBgpInstanceMultipathBgp."
    DEFVAL      { 0 }
    ::= { tBgpPeerGroupAddPathEntry 8 }

tBgpPGAddPathLblIpv4Limit        OBJECT-TYPE
    SYNTAX      TmnxAddPathSendLimit
    MAX-ACCESS  read-create
    STATUS      current
    DESCRIPTION
        "The value of tBgpPGAddPathLblIpv4Limit specifies the maximum number of
         paths per label IPv4 prefix that can be advertised to ADD-PATH peers
         on this peer group.

         An 'inconsistentValue' error is returned if an attempt is made to set
         this object to a value greater than tBgpInstanceMultipathBgp."
    DEFVAL      { 0 }
    ::= { tBgpPeerGroupAddPathEntry 9 }

tBgpPGAddPathLblIpv6Limit        OBJECT-TYPE
    SYNTAX      TmnxAddPathSendLimit
    MAX-ACCESS  read-create
    STATUS      current
    DESCRIPTION
        "The value of tBgpPGAddPathLblIpv6Limit specifies the maximum number of
         paths per label IPv6 prefix that can be advertised to ADD-PATH peers
         on this peer group.

         An 'inconsistentValue' error is returned if an attempt is made to set
         this object to a value greater than tBgpInstanceMultipathBgp."
    DEFVAL      { 0 }
    ::= { tBgpPeerGroupAddPathEntry 10 }

tBgpPGAddPathMvpnIpv4Limit       OBJECT-TYPE
    SYNTAX      Integer32 (0..16)
    MAX-ACCESS  read-create
    STATUS      current
    DESCRIPTION
        "The value of tBgpPGAddPathMvpnIpv4Limit specifies the maximum number
         of paths per MVPN IPv4 prefix that can be advertised to ADD-PATH peers
         on this peer group.

         An 'inconsistentValue' error is returned if an attempt is made to set
         this object to a value greater than tBgpInstanceMultipathBgp."
    DEFVAL      { 0 }
    ::= { tBgpPeerGroupAddPathEntry 11 }

tBgpPGAddPathMvpnIpv6Limit       OBJECT-TYPE
    SYNTAX      Integer32 (0..16)
    MAX-ACCESS  read-create
    STATUS      current
    DESCRIPTION
        "The value of tBgpPGAddPathMvpnIpv6Limit specifies the maximum number
         of paths per MVPN IPv6 prefix that can be advertised to ADD-PATH peers
         on this peer group.

         An 'inconsistentValue' error is returned if an attempt is made to set
         this object to a value greater than tBgpInstanceMultipathBgp."
    DEFVAL      { 0 }
    ::= { tBgpPeerGroupAddPathEntry 12 }

tBgpPGAddPathMcastVpnV4Limit     OBJECT-TYPE
    SYNTAX      Integer32 (0..16)
    MAX-ACCESS  read-create
    STATUS      current
    DESCRIPTION
        "The value of tBgpPGAddPathMcastVpnV4Limit specifies the maximum number
         of paths per Mcast VPN IPv4 prefix that can be advertised to ADD-PATH
         peers on this peer group.

         An 'inconsistentValue' error is returned if an attempt is made to set
         this object to a value greater than tBgpInstanceMultipathBgp."
    DEFVAL      { 0 }
    ::= { tBgpPeerGroupAddPathEntry 13 }

tBgpPGAddPathMcastVpnV6Limit     OBJECT-TYPE
    SYNTAX      Integer32 (0..16)
    MAX-ACCESS  read-create
    STATUS      current
    DESCRIPTION
        "The value of tBgpPGAddPathMcastVpnV6Limit specifies the maximum number
         of paths per Mcast VPN IPv6 prefix that can be advertised to ADD-PATH
         peers on this peer group.

         An 'inconsistentValue' error is returned if an attempt is made to set
         this object to a value greater than tBgpInstanceMultipathBgp."
    DEFVAL      { 0 }
    ::= { tBgpPeerGroupAddPathEntry 14 }

tBgpPGAddPathEvpnLimit           OBJECT-TYPE
    SYNTAX      TmnxAddPathSendLimit
    MAX-ACCESS  read-create
    STATUS      current
    DESCRIPTION
        "The value of tBgpPGAddPathEvpnLimit specifies the maximum
         number of paths per EVPN  prefix that can be advertised to
         ADD-PATH peers on this peer group.

         An 'inconsistentValue' error is returned if an attempt is made to set
         this object to a value greater than tBgpInstanceMultipathBgp."
    DEFVAL      { 0 }
    ::= { tBgpPeerGroupAddPathEntry 15 }

tBgpPGDynNbrIfTableLstChgd       OBJECT-TYPE
    SYNTAX      TimeStamp
    MAX-ACCESS  read-only
    STATUS      current
    DESCRIPTION
        "The value of tBgpPGDynNbrIfTableLstChgd indicates the  timestamp when
         an entry in the tBgpPGDynNbrInterfaceTable was last changed."
    ::= { tBgpPeerGroupObjects 33 }

tBgpPGDynNbrInterfaceTable       OBJECT-TYPE
    SYNTAX      SEQUENCE OF TBgpPGDynNbrInterfaceEntry
    MAX-ACCESS  not-accessible
    STATUS      current
    DESCRIPTION
        "The tBgpPGDynNbrInterfaceTable consists of the information  about BGP
         Group Dynamic Neighbor interfaces."
    ::= { tBgpPeerGroupObjects 34 }

tBgpPGDynNbrInterfaceEntry       OBJECT-TYPE
    SYNTAX      TBgpPGDynNbrInterfaceEntry
    MAX-ACCESS  not-accessible
    STATUS      current
    DESCRIPTION
        "An entry (conceptual row) in the tBgpPGDynNbrInterfaceTable.

         An entry can be created using the row status object,
         tBgpPGDynNbrIfRowStatus. The tBgpPGDynNbrIfGroupName must be set
         during the row creation."
    INDEX       {
        tBgpInstanceIndex,
        tBgpPGDynNbrInterfaceIndex
    }
    ::= { tBgpPGDynNbrInterfaceTable 1 }

TBgpPGDynNbrInterfaceEntry       ::= SEQUENCE
{
    tBgpPGDynNbrInterfaceIndex       InterfaceIndex,
    tBgpPGDynNbrIfLastChanged        TimeStamp,
    tBgpPGDynNbrIfRowStatus          RowStatus,
    tBgpPGDynNbrIfGroupName          BgpPeerGroupName,
    tBgpPGDynNbrIfMaxSessions        Unsigned32
}

tBgpPGDynNbrInterfaceIndex       OBJECT-TYPE
    SYNTAX      InterfaceIndex
    MAX-ACCESS  not-accessible
    STATUS      current
    DESCRIPTION
        "The value of tBgpPGDynNbrInterfaceIndex specifies an interface  index
         (TIMETRA-VRTR-MIB::vRtrIfIndex) of an interface to  associate with
         this BGP group."
    ::= { tBgpPGDynNbrInterfaceEntry 1 }

tBgpPGDynNbrIfLastChanged        OBJECT-TYPE
    SYNTAX      TimeStamp
    MAX-ACCESS  read-only
    STATUS      current
    DESCRIPTION
        "The value of tBgpPGDynNbrIfLastChanged indicates the sysUpTime when
         this row was last modified."
    ::= { tBgpPGDynNbrInterfaceEntry 2 }

tBgpPGDynNbrIfRowStatus          OBJECT-TYPE
    SYNTAX      RowStatus
    MAX-ACCESS  read-create
    STATUS      current
    DESCRIPTION
        "The value of tBgpPGDynNbrIfRowStatus specifies the row status for this
         dynamic neighbor interface entry for this group. It is used to  create
         and delete row entries in this table."
    ::= { tBgpPGDynNbrInterfaceEntry 3 }

tBgpPGDynNbrIfGroupName          OBJECT-TYPE
    SYNTAX      BgpPeerGroupName
    MAX-ACCESS  read-create
    STATUS      current
    DESCRIPTION
        "The value of tBgpPGDynNbrIfGroupName specifies the group name on which
         this interface is configured. This object needs to be set  at row
         creation time."
    ::= { tBgpPGDynNbrInterfaceEntry 4 }

tBgpPGDynNbrIfMaxSessions        OBJECT-TYPE
    SYNTAX      Unsigned32 (1..255)
    MAX-ACCESS  read-create
    STATUS      current
    DESCRIPTION
        "The value of tBgpPGDynNbrIfMaxSessions specifies the maximum number
         of dynamic sessions that are allowed to be setup on the interface  as
         a result of accepting sessions from link-local addresses or initiating
          sessions by means of receiving IPv6 router advertisements."
    DEFVAL      { 1 }
    ::= { tBgpPGDynNbrInterfaceEntry 5 }

tBgpPGDynNbrIfAsRgTblLstChg      OBJECT-TYPE
    SYNTAX      TimeStamp
    MAX-ACCESS  read-only
    STATUS      current
    DESCRIPTION
        "The value of tBgpPGDynNbrIfAsRgTblLstChg indicates the timestamp when
         an entry in the tBgpPGDynNbrIfAsRangeTable was last changed."
    ::= { tBgpPeerGroupObjects 35 }

tBgpPGDynNbrIfAsRangeTable       OBJECT-TYPE
    SYNTAX      SEQUENCE OF TBgpPGDynNbrIfAsRangeEntry
    MAX-ACCESS  not-accessible
    STATUS      current
    DESCRIPTION
        "The tBgpPGDynNbrIfAsRangeTable contains BGP dynamic peering interface
         allowed AS ranges."
    ::= { tBgpPeerGroupObjects 36 }

tBgpPGDynNbrIfAsRangeEntry       OBJECT-TYPE
    SYNTAX      TBgpPGDynNbrIfAsRangeEntry
    MAX-ACCESS  not-accessible
    STATUS      current
    DESCRIPTION
        "An entry (conceptual row) in the tBgpPGDynNbrIfAsRangeTable."
    INDEX       {
        tBgpInstanceIndex,
        tBgpPGDynNbrInterfaceIndex,
        tBgpPGDynNbrIfAsRangeIndex
    }
    ::= { tBgpPGDynNbrIfAsRangeTable 1 }

TBgpPGDynNbrIfAsRangeEntry       ::= SEQUENCE
{
    tBgpPGDynNbrIfAsRangeIndex       Integer32,
    tBgpPGDynNbrIfAsRangeLstChg      TimeStamp,
    tBgpPGDynNbrIfAsRangeMin         Unsigned32,
    tBgpPGDynNbrIfAsRangeMax         Unsigned32
}

tBgpPGDynNbrIfAsRangeIndex       OBJECT-TYPE
    SYNTAX      Integer32 (1..32)
    MAX-ACCESS  not-accessible
    STATUS      current
    DESCRIPTION
        "The value of tBgpPGDynNbrIfAsRangeIndex indicates index used to store
         this range."
    ::= { tBgpPGDynNbrIfAsRangeEntry 1 }

tBgpPGDynNbrIfAsRangeLstChg      OBJECT-TYPE
    SYNTAX      TimeStamp
    MAX-ACCESS  read-only
    STATUS      current
    DESCRIPTION
        "The value of tBgpPGDynNbrIfAsRangeLstChg indicates when this entry was
         last changed."
    ::= { tBgpPGDynNbrIfAsRangeEntry 2 }

tBgpPGDynNbrIfAsRangeMin         OBJECT-TYPE
    SYNTAX      Unsigned32
    MAX-ACCESS  read-create
    STATUS      current
    DESCRIPTION
        "The value of tBgpPGDynNbrIfAsRangeMin specifies the minimum value of
         AS range."
    DEFVAL      { 0 }
    ::= { tBgpPGDynNbrIfAsRangeEntry 3 }

tBgpPGDynNbrIfAsRangeMax         OBJECT-TYPE
    SYNTAX      Unsigned32
    MAX-ACCESS  read-create
    STATUS      current
    DESCRIPTION
        "The value of tBgpPGDynNbrIfAsRangeMax specifies the maximum value of
         AS range."
    DEFVAL      { 0 }
    ::= { tBgpPGDynNbrIfAsRangeEntry 4 }

tBgpPeerObjects                  OBJECT IDENTIFIER ::= { tBgpObjects 4 }

tBgpPeerTableLastChanged         OBJECT-TYPE
    SYNTAX      TimeStamp
    MAX-ACCESS  read-only
    STATUS      current
    DESCRIPTION
        "The value of tBgpPeerTableLastChanged indicates the last timestamp
         when an entry in the tBgpPeerGroupTable was last changed."
    ::= { tBgpPeerObjects 1 }

tBgpPeerTableSpinlock            OBJECT-TYPE
    SYNTAX      TestAndIncr
    MAX-ACCESS  read-write
    STATUS      current
    DESCRIPTION
        "The value of tBgpPeerTableSpinlock specifies voluntary serialization
         control for tBgpPeerGroupTable. It is mainly used to coordinate
         changes to tBgpPeerInheritance."
    DEFVAL      { 0 }
    ::= { tBgpPeerObjects 2 }

tBgpPeerTable                    OBJECT-TYPE
    SYNTAX      SEQUENCE OF TBgpPeerEntry
    MAX-ACCESS  not-accessible
    STATUS      obsolete
    DESCRIPTION
        "The tBgpPeerTable is the list of configured BGP Peers. The table
         entries are indexed by the peer's IP address.  For administrative
         convenience the Peer Group name should be set but is not used for
         sorting in the agent."
    ::= { tBgpPeerObjects 3 }

tBgpPeerEntry                    OBJECT-TYPE
    SYNTAX      TBgpPeerEntry
    MAX-ACCESS  not-accessible
    STATUS      obsolete
    DESCRIPTION
        "An entry (conceptual row) in the tBgpPeerTable.

         An entry can be created using the row status object,
         tBgpPeerRowStatus. When created, all objects are initialized to their
         default values.

         Before the Peer entry can be used, tBgpPeerRowStatus must be set to
         'active(1)'. The Peer entry can be removed by setting
         tBgpPeerRowStatus to 'destroy(6)'.

         The Peer entry will be advertised to BGP peers when tBgpPeerShutdown
         is false."
    INDEX       {
        tBgpInstanceIndex,
        tBgpPeerAddress
    }
    ::= { tBgpPeerTable 1 }

TBgpPeerEntry                    ::= SEQUENCE
{
    tBgpPeerAddress                  IpAddress,
    tBgpPeerPeerGroup                BgpPeerGroupNameOrEmpty,
    tBgpPeerRowStatus                RowStatus,
    tBgpPeerShutdown                 TruthValue,
    tBgpPeerDescription              DisplayString,
    tBgpPeerConnectRetry             BgpConnectRetryTime,
    tBgpPeerHoldTime                 BgpHoldTime,
    tBgpPeerKeepAlive                BgpKeepAliveTime,
    tBgpPeerMinASOrigination         BgpMinASOriginationTime,
    tBgpPeerDampening                TruthValue,
    tBgpPeerLocalAddress             IpAddress,
    tBgpPeerLocalAS                  TmnxBgpAutonomousSystem,
    tBgpPeerLocalPreference          TmnxBgpLocalPreference,
    tBgpPeerLoopDetect               BgpLoopDetect,
    tBgpPeerMinRouteAdvertisement    BgpMinRouteAdvertisement,
    tBgpPeerMaxPrefix                BgpPrefixLimit,
    tBgpPeerMEDSource                BgpMEDSource,
    tBgpPeerMEDValue                 BgpMEDValue,
    tBgpPeerMultihop                 BgpTimeToLive,
    tBgpPeerNextHopSelf              TruthValue,
    tBgpPeerNoAggregatorID           TruthValue,
    tBgpPeerPassive                  TruthValue,
    tBgpPeerPeerAS                   TmnxBgpAutonomousSystem,
    tBgpPeerPeerType                 BgpPeerType,
    tBgpPeerPreference               TmnxBgpPreference,
    tBgpPeerRemovePrivateAS          TruthValue,
    tBgpPeerLastChanged              TimeStamp,
    tBgpPeerInheritance              Counter64,
    tBgpPeerImportPolicy1            TPolicyStatementNameOrEmpty,
    tBgpPeerImportPolicy2            TPolicyStatementNameOrEmpty,
    tBgpPeerImportPolicy3            TPolicyStatementNameOrEmpty,
    tBgpPeerImportPolicy4            TPolicyStatementNameOrEmpty,
    tBgpPeerImportPolicy5            TPolicyStatementNameOrEmpty,
    tBgpPeerExportPolicy1            TPolicyStatementNameOrEmpty,
    tBgpPeerExportPolicy2            TPolicyStatementNameOrEmpty,
    tBgpPeerExportPolicy3            TPolicyStatementNameOrEmpty,
    tBgpPeerExportPolicy4            TPolicyStatementNameOrEmpty,
    tBgpPeerExportPolicy5            TPolicyStatementNameOrEmpty,
    tBgpPeerOperStatus               BgpOperState,
    tBgpPeerLocalASPrivate           TruthValue,
    tBgpPeerMd5Auth                  TruthValue,
    tBgpPeerMd5AuthKey               OCTET STRING,
    tBgpPeerClusterId                IpAddress,
    tBgpPeerDisableClientReflect     TruthValue,
    tBgpPeerGracefulRestart          TruthValue,
    tBgpPeerGRRestartTime            Unsigned32,
    tBgpPeerGRStaleRoute             Unsigned32,
    tBgpPeerGRAdminState             TmnxAdminState,
    tBgpPeerGROperState              TmnxOperState,
    tBgpPeerFamily                   TmnxIpFamily,
    tBgpPeerVpnRemoteFamily          TmnxIpFamily,
    tBgpPeerVpnApplyImport           TruthValue,
    tBgpPeerVpnApplyExport           TruthValue,
    tBgpPeerVpnLocalCaps             TmnxVpnCapability,
    tBgpPeerVpnRemoteCaps            TmnxVpnCapability,
    tBgpPeerConnState                INTEGER,
    tBgpPeerASOverride               TruthValue,
    tBgpPeerOrf                      TruthValue,
    tBgpPeerExtCommsOrf              TruthValue,
    tBgpPeerExtCommsSendOrf          TruthValue,
    tBgpPeerExtCommsRecvOrf          TruthValue
}

tBgpPeerAddress                  OBJECT-TYPE
    SYNTAX      IpAddress
    MAX-ACCESS  not-accessible
    STATUS      obsolete
    DESCRIPTION
        "Index for tBgpPeerTable, tBgpPeerAddress indicates the IP address of
         the Peer."
    ::= { tBgpPeerEntry 1 }

tBgpPeerPeerGroup                OBJECT-TYPE
    SYNTAX      BgpPeerGroupNameOrEmpty
    MAX-ACCESS  read-create
    STATUS      obsolete
    DESCRIPTION
        "The value of tBgpPeerPeerGroup specifies the name of the Peer group
         for the Peer. This object can only be set when the tBgpPeerRowStatus
         is not active(1).

         Setting this object causes the Peer attributes to be set to the
         inherited values from the Peer Group and from the global BGP defaults.

         This will destroy any previously configured values. So, when creating
         a row, set this object first, or second after tBgpPeerAddress. Then
         set any peer attribute objects."
    DEFVAL      { ''H }
    ::= { tBgpPeerEntry 2 }

tBgpPeerRowStatus                OBJECT-TYPE
    SYNTAX      RowStatus
    MAX-ACCESS  read-create
    STATUS      obsolete
    DESCRIPTION
        "The value of tBgpPeerRowStatus specifies the row status for this BGP
         Peer for the virtual router. It is used to create and delete row
         entries in this table.

         In order for an attempt to 'destroy' this row entry to succeed, the
         value of tBgpPeerShutdown must be 'true'."
    ::= { tBgpPeerEntry 3 }

tBgpPeerShutdown                 OBJECT-TYPE
    SYNTAX      TruthValue
    MAX-ACCESS  read-create
    STATUS      obsolete
    DESCRIPTION
        "The value of tBgpPeerShutdown specifies if we advertise this peer or
         not.

         A value of false(2) means no shutdown, so advertise; true(1) means
         this entry is shutdown, so do not advertise."
    DEFVAL      { false }
    ::= { tBgpPeerEntry 4 }

tBgpPeerDescription              OBJECT-TYPE
    SYNTAX      DisplayString (SIZE (0..80))
    MAX-ACCESS  read-create
    STATUS      obsolete
    DESCRIPTION
        "The value of tBgpPeerDescription specifies a user provided description
         string for this peer entry. It can consist of any printable, seven-bit
         ASCII characters up to 80 characters in length."
    DEFVAL      { ''H }
    ::= { tBgpPeerEntry 5 }

tBgpPeerConnectRetry             OBJECT-TYPE
    SYNTAX      BgpConnectRetryTime
    UNITS       "seconds"
    MAX-ACCESS  read-create
    STATUS      obsolete
    DESCRIPTION
        "The value of tBgpPeerConnectRetry specifies the value (in seconds) of
         the BGP Connect Retry timer."
    REFERENCE
        "BGP4-MIB.bgpPeerConnectRetryInterval"
    DEFVAL      { 120 }
    ::= { tBgpPeerEntry 6 }

tBgpPeerHoldTime                 OBJECT-TYPE
    SYNTAX      BgpHoldTime
    UNITS       "seconds"
    MAX-ACCESS  read-create
    STATUS      obsolete
    DESCRIPTION
        "The value of tBgpPeerHoldTime specifies the value (in seconds) of the
         BGP Hold Time."
    REFERENCE
        "BGP4-MIB.bgpPeerHoldTime"
    DEFVAL      { 90 }
    ::= { tBgpPeerEntry 7 }

tBgpPeerKeepAlive                OBJECT-TYPE
    SYNTAX      BgpKeepAliveTime
    UNITS       "seconds"
    MAX-ACCESS  read-create
    STATUS      obsolete
    DESCRIPTION
        "The value of tBgpPeerKeepAlive specifies the value of the BGP
         Keepalive timer.

         A keepalive message is sent every time this timer expires."
    REFERENCE
        "BGP4-MIB.bgpPeerKeepAlive"
    DEFVAL      { 30 }
    ::= { tBgpPeerEntry 8 }

tBgpPeerMinASOrigination         OBJECT-TYPE
    SYNTAX      BgpMinASOriginationTime
    UNITS       "seconds"
    MAX-ACCESS  read-create
    STATUS      obsolete
    DESCRIPTION
        "The value of tBgpPeerMinASOrigination specifies the minimal interval
         (in seconds) at which a given path attribute can be advertised to a
         peer."
    REFERENCE
        "BGP4-MIB.bgpPeerMinASOriginationInterval"
    DEFVAL      { 15 }
    ::= { tBgpPeerEntry 9 }

tBgpPeerDampening                OBJECT-TYPE
    SYNTAX      TruthValue
    MAX-ACCESS  read-create
    STATUS      obsolete
    DESCRIPTION
        "The value of tBgpPeerDampening specifies if route dampening is applied
         to learned routes."
    DEFVAL      { false }
    ::= { tBgpPeerEntry 10 }

tBgpPeerLocalAddress             OBJECT-TYPE
    SYNTAX      IpAddress
    MAX-ACCESS  read-create
    STATUS      obsolete
    DESCRIPTION
        "The value of tBgpPeerLocalAddress specifies the local IP address to be
         used by this peer.

         If set to 0.0.0.0, then use a (non-0.0.0.0) Peer Group Local Address,
         or a (non-0.0.0.0) global Local Address. If both are zero then find
         the local address by querying the closest interface to the peer
         address from the routing table."
    DEFVAL      { '00000000'H }
    ::= { tBgpPeerEntry 11 }

tBgpPeerLocalAS                  OBJECT-TYPE
    SYNTAX      TmnxBgpAutonomousSystem
    MAX-ACCESS  read-create
    STATUS      obsolete
    DESCRIPTION
        "The value of tBgpPeerLocalAS specifies the autonomous system number to
         be advertised for this peer.

         If the value of tBgpPeerLocalAS, the value of tBgpPeerGroupLocalAS or
         tBgpInstanceLocalAS will be used in that order."
    DEFVAL      { 0 }
    ::= { tBgpPeerEntry 12 }

tBgpPeerLocalPreference          OBJECT-TYPE
    SYNTAX      TmnxBgpLocalPreference
    MAX-ACCESS  read-create
    STATUS      obsolete
    DESCRIPTION
        "The value of tBgpPeerLocalPreference specifies the default value for
         the Local Preference attribute. This value is used if the BGP route
         arrives from a BGP peer without the Local Preference attribute set.

         It is overridden by any value set via a route policy."
    DEFVAL      { 100 }
    ::= { tBgpPeerEntry 13 }

tBgpPeerLoopDetect               OBJECT-TYPE
    SYNTAX      BgpLoopDetect
    MAX-ACCESS  read-create
    STATUS      obsolete
    DESCRIPTION
        "The value of tBgpPeerLoopDetect determines how the peer session should
         deal with loop detection in the AS Path."
    DEFVAL      { ignore }
    ::= { tBgpPeerEntry 14 }

tBgpPeerMinRouteAdvertisement    OBJECT-TYPE
    SYNTAX      BgpMinRouteAdvertisement
    UNITS       "seconds"
    MAX-ACCESS  read-create
    STATUS      obsolete
    DESCRIPTION
        "The value of tBgpPeerMinRouteAdvertisement specifies the minimum
         interval at which a given path attribute is advertised to a peer."
    DEFVAL      { 30 }
    ::= { tBgpPeerEntry 15 }

tBgpPeerMaxPrefix                OBJECT-TYPE
    SYNTAX      BgpPrefixLimit
    UNITS       "number of routes"
    MAX-ACCESS  read-create
    STATUS      obsolete
    DESCRIPTION
        "configures the maximum number of routes that can
         be learned from this peer.  zero means 'no limit'.

         if the number of routes exceeds 90% of this limit, then the
         tBgpMaxPrefix90 notification is sent.

         if the number of routes exceeds this limit, then
         BGP peering will be dropped.  Also, the tBgpMaxPrefix100
         notification will be sent."
    DEFVAL      { 0 }
    ::= { tBgpPeerEntry 16 }

tBgpPeerMEDSource                OBJECT-TYPE
    SYNTAX      BgpMEDSource
    MAX-ACCESS  read-create
    STATUS      obsolete
    DESCRIPTION
        "The value of tBgpPeerMEDSource specifies the source of the Multi Exit
         Discriminator (MED) value for peers in this group."
    DEFVAL      { noMedOut }
    ::= { tBgpPeerEntry 17 }

tBgpPeerMEDValue                 OBJECT-TYPE
    SYNTAX      BgpMEDValue
    MAX-ACCESS  read-create
    STATUS      obsolete
    DESCRIPTION
        "The value of tBgpPeerMEDValue specifies the value of MED when
         tBgpPeerMEDSource is 'metricVal'. If the value of tBgpPeerMEDSource is
         not 'metricVal', this object is ignored."
    DEFVAL      { 0 }
    ::= { tBgpPeerEntry 18 }

tBgpPeerMultihop                 OBJECT-TYPE
    SYNTAX      BgpTimeToLive
    UNITS       "TTL hops"
    MAX-ACCESS  read-create
    STATUS      obsolete
    DESCRIPTION
        "The value of tBgpPeerMultihop specifies the TTL used in IP packet
         header for BGP advertisements.

         Default TTL values for EBGP peer is 1, and MAX_TTL for IBGP peers.
         Default value if not set is  no_type - the peer has to infer its value
         based on local-as, and peer-as in that case."
    DEFVAL      { 0 }
    ::= { tBgpPeerEntry 19 }

tBgpPeerNextHopSelf              OBJECT-TYPE
    SYNTAX      TruthValue
    MAX-ACCESS  read-create
    STATUS      obsolete
    DESCRIPTION
        "The value of tBgpPeerNextHopSelf specifies if routes advertised to
         EBGP peers in this group have NEXTHOP path attribute set to this
         router's physical interface.

         When false, third party routes are advertised."
    DEFVAL      { false }
    ::= { tBgpPeerEntry 21 }

tBgpPeerNoAggregatorID           OBJECT-TYPE
    SYNTAX      TruthValue
    MAX-ACCESS  read-create
    STATUS      obsolete
    DESCRIPTION
        "The value of tBgpPeerNoAggregatorID specifies if different routers in
         the same AS create aggregate routes containing different AS paths.

         A value of 'true' would enable setting the router ID to 0 in the
         aggregator path attribute when BGP is aggregating routes.

         A value of 'false' would disable setting the router ID to 0 in the
         aggregator path attribute when BGP is aggregating routes."
    DEFVAL      { false }
    ::= { tBgpPeerEntry 22 }

tBgpPeerPassive                  OBJECT-TYPE
    SYNTAX      TruthValue
    MAX-ACCESS  read-create
    STATUS      obsolete
    DESCRIPTION
        "The value of tBgpPeerPassive specifies if the peer will not attempt to
         connect to the far end peer or just wait for the far end peer to
         connect."
    DEFVAL      { false }
    ::= { tBgpPeerEntry 23 }

tBgpPeerPeerAS                   OBJECT-TYPE
    SYNTAX      TmnxBgpAutonomousSystem
    MAX-ACCESS  read-create
    STATUS      obsolete
    DESCRIPTION
        "The value of tBgpPeerPeerAS specifies the Autonomous System number for
         the remote peer."
    DEFVAL      { 0 }
    ::= { tBgpPeerEntry 24 }

tBgpPeerPeerType                 OBJECT-TYPE
    SYNTAX      BgpPeerType
    MAX-ACCESS  read-create
    STATUS      obsolete
    DESCRIPTION
        "The value of tBgpPeerPeerType specifies the type of peer - noType(1),
         internal(2) and external(3).

         Default value if not set is noType - the peer has to infer its value
         based on local-as, and peer-as in that case."
    DEFVAL      { noType }
    ::= { tBgpPeerEntry 25 }

tBgpPeerPreference               OBJECT-TYPE
    SYNTAX      TmnxBgpPreference (1..255)
    MAX-ACCESS  read-create
    STATUS      obsolete
    DESCRIPTION
        "The value of tBgpPeerPreference specifies the route preference for
         routes learned via the peer."
    DEFVAL      { 170 }
    ::= { tBgpPeerEntry 26 }

tBgpPeerRemovePrivateAS          OBJECT-TYPE
    SYNTAX      TruthValue
    MAX-ACCESS  read-create
    STATUS      obsolete
    DESCRIPTION
        "The value of tBgpPeerRemovePrivateAS specifies if private AS numbers
         should be stripped from the AS Path before advertising them to BGP
         peers."
    DEFVAL      { false }
    ::= { tBgpPeerEntry 27 }

tBgpPeerLastChanged              OBJECT-TYPE
    SYNTAX      TimeStamp
    MAX-ACCESS  read-only
    STATUS      obsolete
    DESCRIPTION
        "The value tBgpPeerLastChanged indicates when an entry in tBgpPeerTable
         was last changed."
    ::= { tBgpPeerEntry 28 }

tBgpPeerInheritance              OBJECT-TYPE
    SYNTAX      Counter64
    MAX-ACCESS  read-create
    STATUS      obsolete
    DESCRIPTION
        "The value of tBgpPeerInheritance specifies if the peer entry in this
         row, should inherit the operational value of an object, or use the
         administratively set value.

         This object is a bit-mask, with the following positions:

         tBgpPeerShutdown                             0x04
         tBgpPeerConnectRetry                         0x10
         tBgpPeerHoldTime                             0x20
         tBgpPeerKeepAlive                            0x40
         tBgpPeerMinASOrigination                     0x80
         tBgpPeerDampening                           0x100
         tBgpPeerLocalAddress                        0x200
         tBgpPeerLocalAS                             0x400
         tBgpPeerLocalPreference                     0x800
         tBgpPeerLoopDetect                         0x1000
         tBgpPeerMinRouteAdvertisement              0x2000
         tBgpPeerMaxPrefix                          0x4000
         tBgpPeerMEDSource                          0x8000
         tBgpPeerMEDValue                          0x10000
         tBgpPeerMultihop                          0x20000
         tBgpPeerNextHopSelf                       0x80000
         tBgpPeerNoAggregatorID                   0x100000
         tBgpPeerPassive                          0x200000
         tBgpPeerPeerAS                           0x400000
         tBgpPeerPeerType                         0x800000
         tBgpPeerPreference                      0x1000000
         tBgpPeerRemovePrivateAS                 0x2000000
         tBgpPeerImportPolicy1                   0x8000000
         tBgpPeerImportPolicy2                  0x10000000
         tBgpPeerImportPolicy3                  0x20000000
         tBgpPeerImportPolicy4                  0x40000000
         tBgpPeerImportPolicy5                  0x80000000
         tBgpPeerExportPolicy1                 0x100000000
         tBgpPeerExportPolicy2                 0x200000000
         tBgpPeerExportPolicy3                 0x400000000
         tBgpPeerExportPolicy4                 0x800000000
         tBgpPeerExportPolicy5                0x1000000000
         tBgpPeerLocalASPrivate               0x2000000000
         tBgpPeerMd5Auth                      0x4000000000
         tBgpPeerMd5AuthKey                   0x8000000000
         tBgpPeerClusterId                   0x10000000000
         tBgpPeerDisableClientReflect        0x20000000000
         tBgpPeerGracefulRestart             0x40000000000
         tBgpPeerGRRestartTime               0x80000000000
         tBgpPeerGRStaleRoute               0x100000000000
         tBgpPeerGRAdminState               0x200000000000
         tBgpPeerFamily                     0x400000000000
         tBgpPeerVpnApplyImport             0x800000000000
         tBgpPeerVpnApplyExport            0x1000000000000
         tBgpPeerASOverride                0x2000000000000
         tBgpPeerOrf                       0x4000000000000
         tBgpPeerExtCommsOrf               0x8000000000000
         tBgpPeerExtCommsSendOrf          0x10000000000000
         tBgpPeerExtCommsRecvOrf          0x20000000000000

         When the bit for an object is set to one, then the object's
         administrative and operational value are whatever the DEFVAL or most
         recently SET value is.

         When the bit for an object is set to zero, then the object's
         administrative and operational value are inherited from the
         corresponding object in tBgpPeerGroupTable, or from the corresponding
         object in tBgpInstanceTable."
    DEFVAL      { 0 }
    ::= { tBgpPeerEntry 29 }

tBgpPeerImportPolicy1            OBJECT-TYPE
    SYNTAX      TPolicyStatementNameOrEmpty
    MAX-ACCESS  read-create
    STATUS      obsolete
    DESCRIPTION
        "The value of tBgpPeerImportPolicy1 specifies import policy number 1
         for peer level."
    DEFVAL      { ''H }
    ::= { tBgpPeerEntry 30 }

tBgpPeerImportPolicy2            OBJECT-TYPE
    SYNTAX      TPolicyStatementNameOrEmpty
    MAX-ACCESS  read-create
    STATUS      obsolete
    DESCRIPTION
        "The value of tBgpPeerImportPolicy2 specifies import policy number 2
         for peer level."
    DEFVAL      { ''H }
    ::= { tBgpPeerEntry 31 }

tBgpPeerImportPolicy3            OBJECT-TYPE
    SYNTAX      TPolicyStatementNameOrEmpty
    MAX-ACCESS  read-create
    STATUS      obsolete
    DESCRIPTION
        "The value of tBgpPeerImportPolicy3 specifies import policy number 3
         for peer level."
    DEFVAL      { ''H }
    ::= { tBgpPeerEntry 32 }

tBgpPeerImportPolicy4            OBJECT-TYPE
    SYNTAX      TPolicyStatementNameOrEmpty
    MAX-ACCESS  read-create
    STATUS      obsolete
    DESCRIPTION
        "The value of tBgpPeerImportPolicy4 specifies import policy number 4
         for peer level."
    DEFVAL      { ''H }
    ::= { tBgpPeerEntry 33 }

tBgpPeerImportPolicy5            OBJECT-TYPE
    SYNTAX      TPolicyStatementNameOrEmpty
    MAX-ACCESS  read-create
    STATUS      obsolete
    DESCRIPTION
        "The value of tBgpPeerImportPolicy5 specifies import policy number 5
         for peer level."
    DEFVAL      { ''H }
    ::= { tBgpPeerEntry 34 }

tBgpPeerExportPolicy1            OBJECT-TYPE
    SYNTAX      TPolicyStatementNameOrEmpty
    MAX-ACCESS  read-create
    STATUS      obsolete
    DESCRIPTION
        "The value of tBgpPeerExportPolicy1 specifies export policy number 1
         for peer level."
    DEFVAL      { ''H }
    ::= { tBgpPeerEntry 35 }

tBgpPeerExportPolicy2            OBJECT-TYPE
    SYNTAX      TPolicyStatementNameOrEmpty
    MAX-ACCESS  read-create
    STATUS      obsolete
    DESCRIPTION
        "The value of tBgpPeerExportPolicy2 specifies export policy number 2
         for peer level."
    DEFVAL      { ''H }
    ::= { tBgpPeerEntry 36 }

tBgpPeerExportPolicy3            OBJECT-TYPE
    SYNTAX      TPolicyStatementNameOrEmpty
    MAX-ACCESS  read-create
    STATUS      obsolete
    DESCRIPTION
        "The value of tBgpPeerExportPolicy3 specifies export policy number 3
         for peer level."
    DEFVAL      { ''H }
    ::= { tBgpPeerEntry 37 }

tBgpPeerExportPolicy4            OBJECT-TYPE
    SYNTAX      TPolicyStatementNameOrEmpty
    MAX-ACCESS  read-create
    STATUS      obsolete
    DESCRIPTION
        "The value of tBgpPeerExportPolicy4 specifies export policy number 4
         for peer level."
    DEFVAL      { ''H }
    ::= { tBgpPeerEntry 38 }

tBgpPeerExportPolicy5            OBJECT-TYPE
    SYNTAX      TPolicyStatementNameOrEmpty
    MAX-ACCESS  read-create
    STATUS      obsolete
    DESCRIPTION
        "The value of tBgpPeerExportPolicy5 specifies export policy number 5
         for peer level."
    DEFVAL      { ''H }
    ::= { tBgpPeerEntry 39 }

tBgpPeerOperStatus               OBJECT-TYPE
    SYNTAX      BgpOperState
    MAX-ACCESS  read-only
    STATUS      obsolete
    DESCRIPTION
        "The value of tBgpPeerOperStatus indicates the operational status of
         this BGP Peer.

         A value of 'inService(2)' means the bgp peer is fully functional.

         A value of 'outOfService(3)' means the bgp peer is down.

         A value of 'transition(4)' means the bgp peer is performing a
         transition from state inService(2) to outOfService(3) or vice versa.

         A value of 'disabled(5)' means the BGP peer needs to be restarted by
         the user."
    ::= { tBgpPeerEntry 40 }

tBgpPeerLocalASPrivate           OBJECT-TYPE
    SYNTAX      TruthValue
    MAX-ACCESS  read-create
    STATUS      obsolete
    DESCRIPTION
        "The value of tBgpPeerLocalASPrivate specifies if the local autonomous
         system number is hidden in paths learned from peering."
    DEFVAL      { false }
    ::= { tBgpPeerEntry 41 }

tBgpPeerMd5Auth                  OBJECT-TYPE
    SYNTAX      TruthValue
    MAX-ACCESS  read-create
    STATUS      obsolete
    DESCRIPTION
        "The value of tBgpPeerMd5Auth specifies if the authentication using MD5
         message based digest protocol is enabled."
    DEFVAL      { false }
    ::= { tBgpPeerEntry 42 }

tBgpPeerMd5AuthKey               OBJECT-TYPE
    SYNTAX      OCTET STRING (SIZE (0..255))
    MAX-ACCESS  read-create
    STATUS      obsolete
    DESCRIPTION
        "The value of tBgpPeerMd5AuthKey specifies the authentication key to be
         used between BGP peers neighbors before establishing sessions.

         Authentication is done using the MD5 message based digest protocol.

         Authentication can be configured globally and applied to all BGP peers
         or per group or per peer. The most specific value is used.

         The authentication key can be any combination of letters or numbers.
         Note that the string CANNOT contain embedded nulls."
    DEFVAL      { ''H }
    ::= { tBgpPeerEntry 43 }

tBgpPeerClusterId                OBJECT-TYPE
    SYNTAX      IpAddress
    MAX-ACCESS  read-create
    STATUS      obsolete
    DESCRIPTION
        "This value of tBgpPeerClusterId specifies the cluster ID for a route
         reflector server.

         A value of 0.0.0.0 indicates that no cluster ID has been assigned to
         the BGP peer."
    DEFVAL      { '00000000'H }
    ::= { tBgpPeerEntry 44 }

tBgpPeerDisableClientReflect     OBJECT-TYPE
    SYNTAX      TruthValue
    MAX-ACCESS  read-create
    STATUS      obsolete
    DESCRIPTION
        "The value of tBgpPeerDisableClientReflect specifies if reflection of
         routes by the route reflector to all client peers within its cluster
         is enabled or disabled.

         A value of 'false' means reflection of routes to all client peers is
         enabled."
    DEFVAL      { false }
    ::= { tBgpPeerEntry 45 }

tBgpPeerGracefulRestart          OBJECT-TYPE
    SYNTAX      TruthValue
    MAX-ACCESS  read-create
    STATUS      obsolete
    DESCRIPTION
        "The value of tBgpPeerGracefulRestart specifies whether or not graceful
         restart capabilities are enabled on this instance of BGP.

         When the value is set to 'false' graceful restart is disabled and any
         previous configuration of other graceful restart parameters is
         removed."
    DEFVAL      { false }
    ::= { tBgpPeerEntry 46 }

tBgpPeerGRRestartTime            OBJECT-TYPE
    SYNTAX      Unsigned32 (0..4095)
    UNITS       "seconds"
    MAX-ACCESS  read-create
    STATUS      obsolete
    DESCRIPTION
        "The value of tBgpPeerGRRestartTime specifies the maximum amount of
         time in seconds that a graceful restart should take."
    DEFVAL      { 300 }
    ::= { tBgpPeerEntry 47 }

tBgpPeerGRStaleRoute             OBJECT-TYPE
    SYNTAX      Unsigned32 (1..3600)
    UNITS       "seconds"
    MAX-ACCESS  read-create
    STATUS      obsolete
    DESCRIPTION
        "The value of tBgpPeerGRStaleRoute specifies the maximum
         amount of time in seconds that stale routes should be maintained
         after a graceful restart is initiated.  This value should be
         at least as large a the value of tBgpPeerGRRestartTime."
    DEFVAL      { 360 }
    ::= { tBgpPeerEntry 48 }

tBgpPeerGRAdminState             OBJECT-TYPE
    SYNTAX      TmnxAdminState
    MAX-ACCESS  read-create
    STATUS      obsolete
    DESCRIPTION
        "The value of tBgpPeerGRAdminState specifies the desired
         administrative state of the graceful restart capabilities for
         this peer of the BGP protocol.  When the value is 'outOfService'
         the graceful restart capabilities are disabled but the
         graceful restart configuration parameters are retained."
    DEFVAL      { inService }
    ::= { tBgpPeerEntry 49 }

tBgpPeerGROperState              OBJECT-TYPE
    SYNTAX      TmnxOperState
    MAX-ACCESS  read-only
    STATUS      obsolete
    DESCRIPTION
        "The value of tBgpPeerGROperState indicates the operational status of
         the graceful restart capabilities for this peer of the BGP protocol."
    ::= { tBgpPeerEntry 50 }

tBgpPeerFamily                   OBJECT-TYPE
    SYNTAX      TmnxIpFamily
    MAX-ACCESS  read-create
    STATUS      obsolete
    DESCRIPTION
        "The value of tBgpPeerFamily specifies the types of routing
         information to be distributed by the local side of this Peer of
         the BGP protocol.  BGP was initially designed for the distribution
         of IPv4 routing information.  Multi-protocol extensions and the
         use of a VPN-IPv4 address have been added to extend its ability
         to carry overlapping routing information.  A 'vpnIpv4' address is
         a 12-byte value consisting of the 8-byte route distinguisher, RD,
         and the 4-byte ipv4 IP address prefix.  The RD must be unique
         within the scope of the VPRN.   This allows the IP address prefixes
         within different VRFs to overlap.

         This object has been obsoleted in release 6.0."
    DEFVAL      { {ipv4} }
    ::= { tBgpPeerEntry 51 }

tBgpPeerVpnRemoteFamily          OBJECT-TYPE
    SYNTAX      TmnxIpFamily
    MAX-ACCESS  read-only
    STATUS      obsolete
    DESCRIPTION
        "The value of tBgpPeerVpnRemoteFamily indicates the types of routing
         information to be distributed by the remote end of this Peer of the
         BGP protocol.  BGP was initially designed for the distribution of
         IPv4 routing information.  Multi-protocol extensions and the use
         of a VPN-IPv4 address have been added to extend its ability to
         carry overlapping routing information.  A 'vpnIpv4' address is a
         12-byte value consisting of the 8-byte route distinguisher, RD,
         and the 4-byte ipv4 IP address prefix.  The RD must be unique
         within the scope of the VPRN.   This allows the IP address prefixes
         within different VRFs to overlap.

         This object has been obsoleted."
    ::= { tBgpPeerEntry 52 }

tBgpPeerVpnApplyImport           OBJECT-TYPE
    SYNTAX      TruthValue
    MAX-ACCESS  read-create
    STATUS      obsolete
    DESCRIPTION
        "The value of tBgpPeerVpnApplyImport specifies if the BGP import route
         policies are applied to VPN-IPv4 routes of this group.

         When the value is 'false' the application of the base instance BGP
         import route policies to VPN-IPv4 routes of this group is disabled."
    DEFVAL      { false }
    ::= { tBgpPeerEntry 53 }

tBgpPeerVpnApplyExport           OBJECT-TYPE
    SYNTAX      TruthValue
    MAX-ACCESS  read-create
    STATUS      obsolete
    DESCRIPTION
        "The value of tBgpPeerVpnApplyExport specifies if the BGP export route
         policies are applied to VPN-IPv4 routes of this group.

         When the value is 'false' the application of the BGP export route
         policies to VPN-IPv4 routes of this group is disabled."
    DEFVAL      { false }
    ::= { tBgpPeerEntry 54 }

tBgpPeerVpnLocalCaps             OBJECT-TYPE
    SYNTAX      TmnxVpnCapability
    MAX-ACCESS  read-only
    STATUS      obsolete
    DESCRIPTION
        "The value of tBgpPeerVpnLocalCaps indicates the capabilities supported
         on the local end of the BGP Peer."
    ::= { tBgpPeerEntry 55 }

tBgpPeerVpnRemoteCaps            OBJECT-TYPE
    SYNTAX      TmnxVpnCapability
    MAX-ACCESS  read-only
    STATUS      obsolete
    DESCRIPTION
        "The value of tBgpPeerVpnRemoteCaps indicates the capabilities
         advertised by the remote end of the BGP Peer."
    ::= { tBgpPeerEntry 56 }

tBgpPeerConnState                OBJECT-TYPE
    SYNTAX      INTEGER {
        idle        (1),
        connect     (2),
        active      (3),
        opensent    (4),
        openconfirm (5),
        established (6)
    }
    MAX-ACCESS  read-only
    STATUS      obsolete
    DESCRIPTION
        "The value of tBgpPeerConnState indicates the BGP peer connection
         state.

         This object is the shadow object of bgpPeerState as existing in the
         BGP4-MIB."
    ::= { tBgpPeerEntry 57 }

tBgpPeerASOverride               OBJECT-TYPE
    SYNTAX      TruthValue
    MAX-ACCESS  read-create
    STATUS      obsolete
    DESCRIPTION
        "The value of tBgpPeerASOverride specifies if the service provider BGP
         will override the customer AS number in the ASPATH with its own AS
         number.

         A value of 'true' means the service provider BGP will override the
         customer AS number in the ASPATH with its own AS number.

         Without this feature there could be scenarios where multiple CE
         locations belonging to the same AS will not be able to communicate due
         to a potential loop detection."
    DEFVAL      { false }
    ::= { tBgpPeerEntry 58 }

tBgpPeerOrf                      OBJECT-TYPE
    SYNTAX      TruthValue
    MAX-ACCESS  read-create
    STATUS      obsolete
    DESCRIPTION
        "The value of tBgpPeerOrf specifies if outbound route filtering
         capability is enabled or disabled for the BGP peer."
    DEFVAL      { false }
    ::= { tBgpPeerEntry 59 }

tBgpPeerExtCommsOrf              OBJECT-TYPE
    SYNTAX      TruthValue
    MAX-ACCESS  read-create
    STATUS      obsolete
    DESCRIPTION
        "The value of tBgpPeerExtCommsOrf specifies if outbound route filtering
         capability is based on extended communities for the BGP peer."
    DEFVAL      { false }
    ::= { tBgpPeerEntry 60 }

tBgpPeerExtCommsSendOrf          OBJECT-TYPE
    SYNTAX      TruthValue
    MAX-ACCESS  read-create
    STATUS      obsolete
    DESCRIPTION
        "The value of tBgpPeerExtCommsSendOrf specifies if outbound route
         filter advertisement to the neighbors in this BGP peer."
    DEFVAL      { false }
    ::= { tBgpPeerEntry 61 }

tBgpPeerExtCommsRecvOrf          OBJECT-TYPE
    SYNTAX      TruthValue
    MAX-ACCESS  read-create
    STATUS      obsolete
    DESCRIPTION
        "The value of tBgpPeerExtCommsRecvOrf specifies if outbound route
         filter for this BGP peer is accepted from the neighbors is enabled."
    DEFVAL      { false }
    ::= { tBgpPeerEntry 62 }

tBgpPeerOperTable                OBJECT-TYPE
    SYNTAX      SEQUENCE OF TBgpPeerOperEntry
    MAX-ACCESS  not-accessible
    STATUS      obsolete
    DESCRIPTION
        "The tBgpPeerOperTable is the list of configured BGP Peers and their
         operational status information."
    ::= { tBgpPeerObjects 4 }

tBgpPeerOperEntry                OBJECT-TYPE
    SYNTAX      TBgpPeerOperEntry
    MAX-ACCESS  not-accessible
    STATUS      obsolete
    DESCRIPTION
        "An entry (conceptual row) in the tBgpPeerOperTable.

         Entries in tBgpPeerOperTable are created when entries are created in
         tBgpPeerTable."
    AUGMENTS    { tBgpPeerEntry }
    ::= { tBgpPeerOperTable 1 }

TBgpPeerOperEntry                ::= SEQUENCE
{
    tBgpPeerOperMsgOctetsRcvd        Counter64,
    tBgpPeerOperMsgOctetsSent        Counter64,
    tBgpPeerOperInputQueueMessages   Gauge32,
    tBgpPeerOperOutputQueueMessages  Gauge32,
    tBgpPeerOperReceivedPrefixes     Counter32,
    tBgpPeerOperSentPrefixes         Counter32,
    tBgpPeerOperActivePrefixes       Gauge32,
    tBgpPeerOperReceivedPaths        Counter32,
    tBgpPeerOperPathsSuppressedByDamping Counter32,
    tBgpPeerOperFlaps                Counter32,
    tBgpPeerOperLastState            BgpPeerState,
    tBgpPeerOperLastEvent            BgpPeerEvent,
    tBgpPeerOperVpnReceivedPrefixes  Counter32,
    tBgpPeerOperVpnSentPrefixes      Counter32,
    tBgpPeerOperVpnActivePrefixes    Gauge32,
    tBgpPeerOperGRSupport            TruthValue,
    tBgpPeerOperGRFamilyRestart      TmnxBGPFamilyType,
    tBgpPeerOperGRFamilyFwding       TmnxBGPFamilyType,
    tBgpPeerOperGRFamilyNegotiated   TmnxBGPFamilyType,
    tBgpPeerOperGRRecvEOR            TmnxBGPFamilyType,
    tBgpPeerOperGRSendEOR            TmnxBGPFamilyType,
    tBgpPeerOperGRStaleRoutesTime    Unsigned32,
    tBgpPeerOperGRRequestRestartTime Unsigned32,
    tBgpPeerOperGRStatus             INTEGER,
    tBgpPeerOperNumRestarts          Unsigned32,
    tBgpPeerOperLastRestartTime      TimeStamp,
    tBgpPeerOperV6ReceivedPrefixes   Counter32,
    tBgpPeerOperV6SentPrefixes       Counter32,
    tBgpPeerOperV6ActivePrefixes     Gauge32,
    tBgpPeerOperV6ReceivedPaths      Counter32,
    tBgpPeerOperV6SuppPathsDamping   Counter32,
    tBgpPeerOperVpnReceivedPaths     Counter32
}

tBgpPeerOperMsgOctetsRcvd        OBJECT-TYPE
    SYNTAX      Counter64
    MAX-ACCESS  read-only
    STATUS      obsolete
    DESCRIPTION
        "The value of tBgpPeerOperMsgOctetsRcvd indicates the number of octets
         received from this peer."
    ::= { tBgpPeerOperEntry 1 }

tBgpPeerOperMsgOctetsSent        OBJECT-TYPE
    SYNTAX      Counter64
    MAX-ACCESS  read-only
    STATUS      obsolete
    DESCRIPTION
        "The value of tBgpPeerOperMsgOctetsSent indicates the number of octets
         transmitted to this peer."
    ::= { tBgpPeerOperEntry 2 }

tBgpPeerOperInputQueueMessages   OBJECT-TYPE
    SYNTAX      Gauge32
    MAX-ACCESS  read-only
    STATUS      obsolete
    DESCRIPTION
        "The value of tBgpPeerOperInputQueueMessages indicates the number of
         unprocessed messages in the queue, from this peer."
    ::= { tBgpPeerOperEntry 3 }

tBgpPeerOperOutputQueueMessages  OBJECT-TYPE
    SYNTAX      Gauge32
    MAX-ACCESS  read-only
    STATUS      obsolete
    DESCRIPTION
        "The value of tBgpPeerOperOutputQueueMessages indicates the number of
         untransmitted messages in the queue, to this peer."
    ::= { tBgpPeerOperEntry 4 }

tBgpPeerOperReceivedPrefixes     OBJECT-TYPE
    SYNTAX      Counter32
    MAX-ACCESS  read-only
    STATUS      obsolete
    DESCRIPTION
        "The value of tBgpPeerOperReceivedPrefixes indicates the number of
         prefixes received from this peer."
    ::= { tBgpPeerOperEntry 5 }

tBgpPeerOperSentPrefixes         OBJECT-TYPE
    SYNTAX      Counter32
    MAX-ACCESS  read-only
    STATUS      obsolete
    DESCRIPTION
        "The value of tBgpPeerOperSentPrefixes indicates the number of prefixes
         transmitted to this peer."
    ::= { tBgpPeerOperEntry 6 }

tBgpPeerOperActivePrefixes       OBJECT-TYPE
    SYNTAX      Gauge32
    MAX-ACCESS  read-only
    STATUS      obsolete
    DESCRIPTION
        "The value of tBgpPeerOperActivePrefixes indicates the number of active
         prefixes from this peer."
    ::= { tBgpPeerOperEntry 7 }

tBgpPeerOperReceivedPaths        OBJECT-TYPE
    SYNTAX      Counter32
    MAX-ACCESS  read-only
    STATUS      obsolete
    DESCRIPTION
        "The value of tBgpPeerOperReceivedPaths indicates the number of paths
         received from this peer."
    ::= { tBgpPeerOperEntry 8 }

tBgpPeerOperPathsSuppressedByDamping OBJECT-TYPE
    SYNTAX      Counter32
    MAX-ACCESS  read-only
    STATUS      obsolete
    DESCRIPTION
        "The value of tBgpPeerOperPathsSuppressedByDamping indicates the number
         of paths from this peer, which have been suppressed by damping."
    ::= { tBgpPeerOperEntry 9 }

tBgpPeerOperFlaps                OBJECT-TYPE
    SYNTAX      Counter32
    MAX-ACCESS  read-only
    STATUS      obsolete
    DESCRIPTION
        "The value of tBgpPeerOperFlaps indicates the number of flaps of
         updates from this peer."
    ::= { tBgpPeerOperEntry 10 }

tBgpPeerOperLastState            OBJECT-TYPE
    SYNTAX      BgpPeerState
    MAX-ACCESS  read-only
    STATUS      obsolete
    DESCRIPTION
        "The value of tBgpPeerOperLastState indicates the last BGP state of
         this peer."
    ::= { tBgpPeerOperEntry 11 }

tBgpPeerOperLastEvent            OBJECT-TYPE
    SYNTAX      BgpPeerEvent
    MAX-ACCESS  read-only
    STATUS      obsolete
    DESCRIPTION
        "The value of tBgpPeerOperLastEvent indicates the last BGP event of
         this peer."
    ::= { tBgpPeerOperEntry 12 }

tBgpPeerOperVpnReceivedPrefixes  OBJECT-TYPE
    SYNTAX      Counter32
    MAX-ACCESS  read-only
    STATUS      obsolete
    DESCRIPTION
        "The value of tBgpPeerOperVpnReceivedPrefixes indicates the number of
         received VPN prefixes."
    ::= { tBgpPeerOperEntry 13 }

tBgpPeerOperVpnSentPrefixes      OBJECT-TYPE
    SYNTAX      Counter32
    MAX-ACCESS  read-only
    STATUS      obsolete
    DESCRIPTION
        "The value of tBgpPeerOperVpnSentPrefixes indicates the number of
         transmitted VPN prefixes."
    ::= { tBgpPeerOperEntry 14 }

tBgpPeerOperVpnActivePrefixes    OBJECT-TYPE
    SYNTAX      Gauge32
    MAX-ACCESS  read-only
    STATUS      obsolete
    DESCRIPTION
        "The value of tBgpPeerOperVpnActivePrefixes indicates the number of
         active VPN prefixes from this BGP peer."
    ::= { tBgpPeerOperEntry 15 }

tBgpPeerOperGRSupport            OBJECT-TYPE
    SYNTAX      TruthValue
    MAX-ACCESS  read-only
    STATUS      obsolete
    DESCRIPTION
        "The value of tBgpPeerOperGRSupport indicates whether the BGP peer
         supports graceful restart. If tBgpPeerOperGRSupport has a value of
         'true' the peer supports graceful restart."
    ::= { tBgpPeerOperEntry 16 }

tBgpPeerOperGRFamilyRestart      OBJECT-TYPE
    SYNTAX      TmnxBGPFamilyType
    MAX-ACCESS  read-only
    STATUS      obsolete
    DESCRIPTION
        "The value of tBgpPeerOperGRFamilyRestart indicates the capability type
         of NLRI that peer supports restart for."
    ::= { tBgpPeerOperEntry 17 }

tBgpPeerOperGRFamilyFwding       OBJECT-TYPE
    SYNTAX      TmnxBGPFamilyType
    MAX-ACCESS  read-only
    STATUS      obsolete
    DESCRIPTION
        "The value of tBgpPeerOperGRFamilyFwding indicates the capability type
         of NLRI that peer saved forwarding for."
    ::= { tBgpPeerOperEntry 18 }

tBgpPeerOperGRFamilyNegotiated   OBJECT-TYPE
    SYNTAX      TmnxBGPFamilyType
    MAX-ACCESS  read-only
    STATUS      obsolete
    DESCRIPTION
        "The value of tBgpPeerOperGRFamilyNegotiated indicates the capability
         type of NLRI that restart is negotiated for by the peer."
    ::= { tBgpPeerOperEntry 19 }

tBgpPeerOperGRRecvEOR            OBJECT-TYPE
    SYNTAX      TmnxBGPFamilyType
    MAX-ACCESS  read-only
    STATUS      obsolete
    DESCRIPTION
        "The value of tBgpPeerOperGRRecvEOR indicates the capability type of
         NLRI of received end-of-rib markers from the peer."
    ::= { tBgpPeerOperEntry 20 }

tBgpPeerOperGRSendEOR            OBJECT-TYPE
    SYNTAX      TmnxBGPFamilyType
    MAX-ACCESS  read-only
    STATUS      obsolete
    DESCRIPTION
        "The value of tBgpPeerOperGRSendEOR indicates the capability type of
         NLRI of all the sent end-of-rib markers by the peer."
    ::= { tBgpPeerOperEntry 21 }

tBgpPeerOperGRStaleRoutesTime    OBJECT-TYPE
    SYNTAX      Unsigned32
    MAX-ACCESS  read-only
    STATUS      obsolete
    DESCRIPTION
        "The value of tBgpPeerOperGRStaleRoutesTime indicates the maximum
         amount of time in seconds that stale routes are maintained by the peer
         after a graceful restart is initiated."
    ::= { tBgpPeerOperEntry 22 }

tBgpPeerOperGRRequestRestartTime OBJECT-TYPE
    SYNTAX      Unsigned32
    MAX-ACCESS  read-only
    STATUS      obsolete
    DESCRIPTION
        "The value of tBgpPeerOperGRRequestRestartTime indicates the maximum
         amount of time in seconds that a graceful restart takes for the peer."
    ::= { tBgpPeerOperEntry 23 }

tBgpPeerOperGRStatus             OBJECT-TYPE
    SYNTAX      INTEGER {
        notHelping       (1),
        restarting       (2),
        restart-complete (3),
        helping          (4)
    }
    MAX-ACCESS  read-only
    STATUS      obsolete
    DESCRIPTION
        "The value of tBgpPeerOperGRStatus indicates the graceful restart
         status of the BGP peer.'

         The values of tBgpPeerOperGRStatus means:
            notHelping (1),         -- Peer is not currently being helped
            restarting (2),         -- Received restart request from the peer
            restart-complete (3),   -- The peer has completed the most recent restart
            helping (4)             -- Peer is helping us in restarting."
    ::= { tBgpPeerOperEntry 24 }

tBgpPeerOperNumRestarts          OBJECT-TYPE
    SYNTAX      Unsigned32
    MAX-ACCESS  read-only
    STATUS      obsolete
    DESCRIPTION
        "The value of tBgpPeerOperNumRestarts indicates the number of times the
         peer has attempted restart."
    ::= { tBgpPeerOperEntry 25 }

tBgpPeerOperLastRestartTime      OBJECT-TYPE
    SYNTAX      TimeStamp
    MAX-ACCESS  read-only
    STATUS      obsolete
    DESCRIPTION
        "The value of tBgpPeerOperLastRestartTime indicates the last time the
         peer attempted restart."
    ::= { tBgpPeerOperEntry 26 }

tBgpPeerOperV6ReceivedPrefixes   OBJECT-TYPE
    SYNTAX      Counter32
    MAX-ACCESS  read-only
    STATUS      obsolete
    DESCRIPTION
        "The value of tBgpPeerOperV6ReceivedPrefixes indicates the number of
         IPv6 prefixes received from this peer."
    ::= { tBgpPeerOperEntry 27 }

tBgpPeerOperV6SentPrefixes       OBJECT-TYPE
    SYNTAX      Counter32
    MAX-ACCESS  read-only
    STATUS      obsolete
    DESCRIPTION
        "The value of tBgpPeerOperV6SentPrefixes indicates the number of IPv6
         prefixes transmitted to this peer."
    ::= { tBgpPeerOperEntry 28 }

tBgpPeerOperV6ActivePrefixes     OBJECT-TYPE
    SYNTAX      Gauge32
    MAX-ACCESS  read-only
    STATUS      obsolete
    DESCRIPTION
        "The value of tBgpPeerOperV6ActivePrefixes indicates the number of
         active IPv6 prefixes from this peer."
    ::= { tBgpPeerOperEntry 29 }

tBgpPeerOperV6ReceivedPaths      OBJECT-TYPE
    SYNTAX      Counter32
    MAX-ACCESS  read-only
    STATUS      obsolete
    DESCRIPTION
        "The value of tBgpPeerOperV6ReceivedPaths indicates the number of IPv6
         paths received from this peer."
    ::= { tBgpPeerOperEntry 30 }

tBgpPeerOperV6SuppPathsDamping   OBJECT-TYPE
    SYNTAX      Counter32
    MAX-ACCESS  read-only
    STATUS      obsolete
    DESCRIPTION
        "The value of tBgpPeerOperV6SuppPathsDamping indicates the number of
         IPv6 paths from this peer, which have been suppressed by damping."
    ::= { tBgpPeerOperEntry 31 }

tBgpPeerOperVpnReceivedPaths     OBJECT-TYPE
    SYNTAX      Counter32
    MAX-ACCESS  read-only
    STATUS      obsolete
    DESCRIPTION
        "The value of tBgpPeerOperVpnReceivedPaths indicates the number of VPN
         paths received from this peer."
    ::= { tBgpPeerOperEntry 32 }

tBgpPeerSendOrfRouteTargetTable  OBJECT-TYPE
    SYNTAX      SEQUENCE OF TBgpPeerSendOrfRouteTargetEntry
    MAX-ACCESS  not-accessible
    STATUS      obsolete
    DESCRIPTION
        "The table contains information about the route targets to be
         advertised to the peers if it is Outbound route filtering capable."
    ::= { tBgpPeerObjects 5 }

tBgpPeerSendOrfRouteTargetEntry  OBJECT-TYPE
    SYNTAX      TBgpPeerSendOrfRouteTargetEntry
    MAX-ACCESS  not-accessible
    STATUS      obsolete
    DESCRIPTION
        "An entry in the tBgpPeerSendOrfRouteTargetTable.

         Each entry represents a route target to be advertised  to the peer."
    INDEX       {
        tBgpInstanceIndex,
        tBgpPeerAddress,
        IMPLIED tBgpPeerSendOrfRouteTarget
    }
    ::= { tBgpPeerSendOrfRouteTargetTable 1 }

TBgpPeerSendOrfRouteTargetEntry  ::= SEQUENCE
{
    tBgpPeerSendOrfRouteTarget       TNamedItem,
    tBgpPeerSendOrfRTRowStatus       RowStatus
}

tBgpPeerSendOrfRouteTarget       OBJECT-TYPE
    SYNTAX      TNamedItem
    MAX-ACCESS  not-accessible
    STATUS      obsolete
    DESCRIPTION
        "Index for the tBgpPeerSendOrfRouteTargetTable. The value of
         tBgpPeerSendOrfRouteTarget specifies the extended community name to be
         advertised to the peer."
    ::= { tBgpPeerSendOrfRouteTargetEntry 1 }

tBgpPeerSendOrfRTRowStatus       OBJECT-TYPE
    SYNTAX      RowStatus
    MAX-ACCESS  read-create
    STATUS      obsolete
    DESCRIPTION
        "RowStatus for the Send Orf Route target entry."
    ::= { tBgpPeerSendOrfRouteTargetEntry 2 }

tBgpPeerParamsTable              OBJECT-TYPE
    SYNTAX      SEQUENCE OF TBgpPeerParamsEntry
    MAX-ACCESS  not-accessible
    STATUS      obsolete
    DESCRIPTION
        "The table contains information about the attributes configured for the
         BGP instance."
    ::= { tBgpPeerObjects 6 }

tBgpPeerParamsEntry              OBJECT-TYPE
    SYNTAX      TBgpPeerParamsEntry
    MAX-ACCESS  not-accessible
    STATUS      obsolete
    DESCRIPTION
        "An entry in the tBgpPeerParamsTable. Each entry maintains the
         attributes configured for BGP instance."
    INDEX       {
        tBgpInstanceIndex,
        tBgpPeerAddress
    }
    ::= { tBgpPeerParamsTable 1 }

TBgpPeerParamsEntry              ::= SEQUENCE
{
    tBgpPeerParamsInheritance        Counter64,
    tBgpPeerDisableFEFailover        TruthValue,
    tBgpPeerDisableComms             TruthValue,
    tBgpPeerDisableExtComms          TruthValue,
    tBgpPeerDefaultOriginate         TruthValue,
    tBgpPeerAdvertiseInactiveRts     TruthValue,
    tBgpPeerMinTTLValue              Unsigned32,
    tBgpPeerTTLLogId                 TFilterLogId
}

tBgpPeerParamsInheritance        OBJECT-TYPE
    SYNTAX      Counter64
    MAX-ACCESS  read-create
    STATUS      obsolete
    DESCRIPTION
        "The value of tBgpPeerParamsInheritance specifies if the peer entry in
         this row, should inherit the operational value of an object, or use
         the administratively set value.

         This object is a bit-mask, with the following positions:

         tBgpPeerDisableFEFailover        0x0000000000000002
         tBgpPeerDisableComms             0x0000000000000004
         tBgpPeerDisableExtComms          0x0000000000000008
         tBgpPeerDefaultOriginate         0x0000000000000010
         tBgpPeerAdvertiseInactiveRts     0x0000000000000020
         tBgpPeerMinTTLValue              0x0000000000000040
         tBgpPeerTTLLogId                 0x0000000000000080

         When the bit for an object is set to one, then the object's
         administrative and operational value are whatever the DEFVAL or most
         recently SET value is.

         When the bit for an object is set to zero, then the object's
         administrative and operational value are inherited from the
         corresponding object in tBgpPeerGroupTable, or from the corresponding
         object in tBgpInstanceTable.

         By default all of these attributes should be inherited from the
         tBgpPeerGroupTable."
    DEFVAL      { 0 }
    ::= { tBgpPeerParamsEntry 1 }

tBgpPeerDisableFEFailover        OBJECT-TYPE
    SYNTAX      TruthValue
    MAX-ACCESS  read-create
    STATUS      obsolete
    DESCRIPTION
        "The value of  tBgpPeerDisableFEFailover controls whether
         the router should drop an external BGP session immediately
         when the local interface goes down, or whether the BGP
         session should be kept up until the holdtime expires.

         Setting the value to 'true' causes the external BGP session to go down
         immediately when the local interface goes down."
    DEFVAL      { false }
    ::= { tBgpPeerParamsEntry 2 }

tBgpPeerDisableComms             OBJECT-TYPE
    SYNTAX      TruthValue
    MAX-ACCESS  read-create
    STATUS      obsolete
    DESCRIPTION
        "The value of tBgpPeerDisableComms enables or disables sending of
         community attribute to the peer for non-external communities."
    DEFVAL      { false }
    ::= { tBgpPeerParamsEntry 3 }

tBgpPeerDisableExtComms          OBJECT-TYPE
    SYNTAX      TruthValue
    MAX-ACCESS  read-create
    STATUS      obsolete
    DESCRIPTION
        "The value of tBgpPeerDisableExtComms enables or disables sending of
         community attribute to the peers for external communities."
    DEFVAL      { false }
    ::= { tBgpPeerParamsEntry 4 }

tBgpPeerDefaultOriginate         OBJECT-TYPE
    SYNTAX      TruthValue
    MAX-ACCESS  read-create
    STATUS      obsolete
    DESCRIPTION
        "The value of tBgpPeerDefaultOriginate enables or disables the sending
         of default routes to the peer, making it independent of the route
         policies."
    DEFVAL      { false }
    ::= { tBgpPeerParamsEntry 5 }

tBgpPeerAdvertiseInactiveRts     OBJECT-TYPE
    SYNTAX      TruthValue
    MAX-ACCESS  read-create
    STATUS      obsolete
    DESCRIPTION
        "The value of tBgpPeerAdvertiseInactiveRts enables or disables
         advertising of inactive BGP routes to other BGP peers."
    DEFVAL      { false }
    ::= { tBgpPeerParamsEntry 6 }

tBgpPeerMinTTLValue              OBJECT-TYPE
    SYNTAX      Unsigned32 (0 | 1..255)
    MAX-ACCESS  read-create
    STATUS      obsolete
    DESCRIPTION
        "The value of tBgpPeerMinTTLValue specifies the minimum TTL value for
         an incoming BGP packet.

         If tBgpPeerMinTTLValue is set to zero (0), the TTL Security feature is
         disabled."
    DEFVAL      { 0 }
    ::= { tBgpPeerParamsEntry 7 }

tBgpPeerTTLLogId                 OBJECT-TYPE
    SYNTAX      TFilterLogId
    MAX-ACCESS  read-create
    STATUS      obsolete
    DESCRIPTION
        "The value of tBgpPeerTTLLogId specifies the filter log to use for
         packets that fail TTL security check. The value zero indicates that
         logging is disabled."
    DEFVAL      { 0 }
    ::= { tBgpPeerParamsEntry 8 }

tBgpPeerNgTable                  OBJECT-TYPE
    SYNTAX      SEQUENCE OF TBgpPeerNgEntry
    MAX-ACCESS  not-accessible
    STATUS      current
    DESCRIPTION
        "The tBgpPeerNgTable is the list of configured BGP IPV4 and IPV6 Peers.

         The table entries are indexed by BGP instance, peer address type and
         the peer's IP address. For administrative convenience the Peer Group
         name should be set but is not used for sorting in the agent."
    ::= { tBgpPeerObjects 7 }

tBgpPeerNgEntry                  OBJECT-TYPE
    SYNTAX      TBgpPeerNgEntry
    MAX-ACCESS  not-accessible
    STATUS      current
    DESCRIPTION
        "Defines an entry (conceptual row) in the tBgpPeerNgTable.

         An entry can be created using the row status object,
         tBgpPeerNgRowStatus. When created, all objects are initialized to
         their default values.

         Before the Peer entry can be used, tBgpPeerNgRowStatus
         must be set to 'active(1)'.  the Peer entry can be removed
         by setting tBgpPeerNgRowStatus to 'destroy(6)'.

         The Peer entry will be advertised to BGP peers when tBgpPeerNgShutdown
         is false."
    INDEX       {
        tBgpPeerNgInstanceIndex,
        tBgpPeerNgAddressType,
        tBgpPeerNgAddress
    }
    ::= { tBgpPeerNgTable 1 }

TBgpPeerNgEntry                  ::= SEQUENCE
{
    tBgpPeerNgInstanceIndex          TmnxVRtrID,
    tBgpPeerNgAddressType            InetAddressType,
    tBgpPeerNgAddress                InetAddress,
    tBgpPeerNgPeerGroup              BgpPeerGroupNameOrEmpty,
    tBgpPeerNgRowStatus              RowStatus,
    tBgpPeerNgShutdown               TmnxAdminStateTruthValue,
    tBgpPeerNgDescription            DisplayString,
    tBgpPeerNgConnectRetry           BgpConnectRetryTime,
    tBgpPeerNgHoldTime               BgpHoldTime,
    tBgpPeerNgKeepAlive              BgpKeepAliveTime,
    tBgpPeerNgMinASOrigination       BgpMinASOriginationTime,
    tBgpPeerNgDampening              TruthValue,
    tBgpPeerNgLocalAddress           InetAddress,
    tBgpPeerNgLocalAddressType       InetAddressType,
    tBgpPeerNgLocalAS                TmnxBgpAutonomousSystem,
    tBgpPeerNgLocalPreference        TmnxBgpLocalPreference,
    tBgpPeerNgLoopDetect             BgpLoopDetect,
    tBgpPeerNgMinRouteAdvertisement  BgpMinRouteAdvertisement,
    tBgpPeerNgMaxPrefix              BgpPrefixLimit,
    tBgpPeerNgMEDSource              BgpMEDSource,
    tBgpPeerNgMEDValue               BgpMEDValue,
    tBgpPeerNgMultihop               BgpTimeToLive,
    tBgpPeerNgNextHopSelf            TruthValue,
    tBgpPeerNgNoAggregatorID         TruthValue,
    tBgpPeerNgPassive                TruthValue,
    tBgpPeerNgPeerAS                 TmnxBgpAutonomousSystem,
    tBgpPeerNgPeerType               BgpPeerType,
    tBgpPeerNgPreference             TmnxBgpPreference,
    tBgpPeerNgRemovePrivateAS        TruthValue,
    tBgpPeerNgLastChanged            TimeStamp,
    tBgpPeerNgInheritance            Counter64,
    tBgpPeerNgImportPolicy1          TPolicyStatementNameOrEmpty,
    tBgpPeerNgImportPolicy2          TPolicyStatementNameOrEmpty,
    tBgpPeerNgImportPolicy3          TPolicyStatementNameOrEmpty,
    tBgpPeerNgImportPolicy4          TPolicyStatementNameOrEmpty,
    tBgpPeerNgImportPolicy5          TPolicyStatementNameOrEmpty,
    tBgpPeerNgExportPolicy1          TPolicyStatementNameOrEmpty,
    tBgpPeerNgExportPolicy2          TPolicyStatementNameOrEmpty,
    tBgpPeerNgExportPolicy3          TPolicyStatementNameOrEmpty,
    tBgpPeerNgExportPolicy4          TPolicyStatementNameOrEmpty,
    tBgpPeerNgExportPolicy5          TPolicyStatementNameOrEmpty,
    tBgpPeerNgOperStatus             BgpOperState,
    tBgpPeerNgLocalASPrivate         TruthValue,
    tBgpPeerNgMd5Auth                TruthValue,
    tBgpPeerNgMd5AuthKey             DisplayString,
    tBgpPeerNgClusterId              IpAddress,
    tBgpPeerNgDisableClientReflect   TruthValue,
    tBgpPeerNgGracefulRestart        TruthValue,
    tBgpPeerNgGRRestartTime          Unsigned32,
    tBgpPeerNgGRStaleRoute           Unsigned32,
    tBgpPeerNgGRAdminState           TmnxAdminState,
    tBgpPeerNgGROperState            TmnxOperState,
    tBgpPeerNgFamily                 TmnxIpFamily,
    tBgpPeerNgVpnRemoteFamily        TmnxIpFamily,
    tBgpPeerNgVpnApplyImport         TruthValue,
    tBgpPeerNgVpnApplyExport         TruthValue,
    tBgpPeerNgVpnLocalCaps           TmnxVpnCapability,
    tBgpPeerNgVpnRemoteCaps          TmnxVpnCapability,
    tBgpPeerNgConnState              INTEGER,
    tBgpPeerNgASOverride             TruthValue,
    tBgpPeerNgOrf                    TruthValue,
    tBgpPeerNgExtCommsOrf            TruthValue,
    tBgpPeerNgExtCommsSendOrf        TruthValue,
    tBgpPeerNgExtCommsRecvOrf        TruthValue,
    tBgpPeerNgLocalAS4Byte           InetAutonomousSystemNumber,
    tBgpPeerNgPeerAS4Byte            InetAutonomousSystemNumber,
    tBgpPeerNgDisable4ByteASN        TruthValue,
    tBgpPeerNgHoldTimeIsStrict       TruthValue,
    tBgpPeerNgL2vpnCiscoInterop      TruthValue,
    tBgpPeerNgRemovePrivateASLmtd    TruthValue,
    tBgpPeerNgMaxPrefixLogOnly       TruthValue,
    tBgpPeerNgMaxPrefixThreshold     Unsigned32,
    tBgpPeerNgDisableCapNegotiation  TruthValue,
    tBgpPeerNgCreationType           INTEGER
}

tBgpPeerNgInstanceIndex          OBJECT-TYPE
    SYNTAX      TmnxVRtrID
    MAX-ACCESS  not-accessible
    STATUS      current
    DESCRIPTION
        "tBgpPeerNgInstanceIndex is the bgp instance index for tBgpPeerNgTable."
    ::= { tBgpPeerNgEntry 1 }

tBgpPeerNgAddressType            OBJECT-TYPE
    SYNTAX      InetAddressType
    MAX-ACCESS  not-accessible
    STATUS      current
    DESCRIPTION
        "Index for tBgpPeerNgTable. The tBgpPeerNgAddressType indicates the IP
         address type of the Peer."
    ::= { tBgpPeerNgEntry 2 }

tBgpPeerNgAddress                OBJECT-TYPE
    SYNTAX      InetAddress (SIZE (4|16|20))
    MAX-ACCESS  not-accessible
    STATUS      current
    DESCRIPTION
        "Index for tBgpPeerNgTable. tBgpPeerNgAddress indicates the IPv(4/6)
         address of the Peer.

         If tBgpPeerNgAddressType is 'ipv4', then tBgpPeerNgAddress object
         expects an ipv4 address.

         If tBgpPeerNgAddressType is 'ipv6', then tBgpPeerNgAddress object
         should be a 16-octet value ipv6 address."
    ::= { tBgpPeerNgEntry 3 }

tBgpPeerNgPeerGroup              OBJECT-TYPE
    SYNTAX      BgpPeerGroupNameOrEmpty
    MAX-ACCESS  read-create
    STATUS      current
    DESCRIPTION
        "The value of tBgpPeerNgPeerGroup specifies the name of the Peer group
         for the Peer. This object can only be set when the tBgpPeerNgRowStatus
         is not active(1).

         Setting this object causes the Peer attributes to be set to the
         inherited values from the Peer Group and from the global BGP defaults.
         This will destroy any previously configured values. So, when creating
         a row, set this object first, or second after tBgpPeerNgAddress. Then,
         set any peer attribute objects."
    DEFVAL      { ''H }
    ::= { tBgpPeerNgEntry 4 }

tBgpPeerNgRowStatus              OBJECT-TYPE
    SYNTAX      RowStatus
    MAX-ACCESS  read-create
    STATUS      current
    DESCRIPTION
        "The value of tBgpPeerNgRowStatus specifies the row status for this BGP
         instance for the virtual router. It is used to create and delete row
         entries in this table.

         In order for an attempt to 'destroy' this row entry to succeed, the
         value of tBgpPeerNgShutdown must be 'true'."
    ::= { tBgpPeerNgEntry 5 }

tBgpPeerNgShutdown               OBJECT-TYPE
    SYNTAX      TmnxAdminStateTruthValue
    MAX-ACCESS  read-create
    STATUS      current
    DESCRIPTION
        "The value of tBgpPeerNgShutdown specifies if we advertise this peer or
         not.

         A value of false(2) means no shutdown, so advertise; true(1) means
         this entry is shutdown, so do not advertise."
    DEFVAL      { false }
    ::= { tBgpPeerNgEntry 6 }

tBgpPeerNgDescription            OBJECT-TYPE
    SYNTAX      DisplayString (SIZE (0..80))
    MAX-ACCESS  read-create
    STATUS      current
    DESCRIPTION
        "The value of tBgpPeerNgDescription specifies a user provided
         description string for this Peer Group. It can consist of any
         printable, seven-bit ASCII characters up to 80 characters in length."
    DEFVAL      { ''H }
    ::= { tBgpPeerNgEntry 7 }

tBgpPeerNgConnectRetry           OBJECT-TYPE
    SYNTAX      BgpConnectRetryTime
    UNITS       "seconds"
    MAX-ACCESS  read-create
    STATUS      current
    DESCRIPTION
        "The value of tBgpPeerNgConnectRetry specifies the value (in seconds)
         of the BGP Connect Retry timer."
    REFERENCE
        "BGP4-MIB.bgpPeerConnectRetryInterval"
    DEFVAL      { 120 }
    ::= { tBgpPeerNgEntry 8 }

tBgpPeerNgHoldTime               OBJECT-TYPE
    SYNTAX      BgpHoldTime
    UNITS       "seconds"
    MAX-ACCESS  read-create
    STATUS      current
    DESCRIPTION
        "The value of tBgpPeerNgHoldTime specifies the value (in seconds) of
         the BGP Hold Time."
    REFERENCE
        "BGP4-MIB.bgpPeerHoldTime"
    DEFVAL      { 90 }
    ::= { tBgpPeerNgEntry 9 }

tBgpPeerNgKeepAlive              OBJECT-TYPE
    SYNTAX      BgpKeepAliveTime
    UNITS       "seconds"
    MAX-ACCESS  read-create
    STATUS      current
    DESCRIPTION
        "The value of tBgpPeerNgKeepAlive specifies the value of the BGP
         Keepalive timer.

         A keepalive message is sent every time this timer expires."
    REFERENCE
        "BGP4-MIB.bgpPeerKeepAlive"
    DEFVAL      { 30 }
    ::= { tBgpPeerNgEntry 10 }

tBgpPeerNgMinASOrigination       OBJECT-TYPE
    SYNTAX      BgpMinASOriginationTime
    UNITS       "seconds"
    MAX-ACCESS  read-create
    STATUS      obsolete
    DESCRIPTION
        "The value of tBgpPeerNgMinASOrigination specifies the minimal interval
         (in seconds) at which a given path attribute can be advertised to a
         peer.

         This object was obsoleted in release 12.0."
    REFERENCE
        "BGP4-MIB.bgpPeerMinASOriginationInterval"
    DEFVAL      { 15 }
    ::= { tBgpPeerNgEntry 11 }

tBgpPeerNgDampening              OBJECT-TYPE
    SYNTAX      TruthValue
    MAX-ACCESS  read-create
    STATUS      current
    DESCRIPTION
        "The value of tBgpPeerNgDampening specifies if route dampening is
         applied to learned routes."
    DEFVAL      { false }
    ::= { tBgpPeerNgEntry 12 }

tBgpPeerNgLocalAddress           OBJECT-TYPE
    SYNTAX      InetAddress (SIZE (0|4|16))
    MAX-ACCESS  read-create
    STATUS      current
    DESCRIPTION
        "The value of tBgpPeerNgLocalAddress specifies the local IP address the
         peer group or Peer is to use as advertisement source address.

         If the tBgpPeerNgLocalAddressType is set to ipv4, then the local
         address is an ipv4 address, if the tBgpPeerNgLocalAddressType is set
         to ipv6, the local address of the peer is an ipv6 address.

         If tBgpPeerNgLocalAddress is set to 0.0.0.0, then use a (non-0.0.0.0)
         Peer Group Local Address, or a (non-0.0.0.0) global Local Address, If
         both are zero then find the local address by querying the closest
         interface to the peer address from the routing table.

         If local address is not set, tBgpPeerNgLocalAddressType is set to
         unknown and tBgpPeerNgLocalAddress returns a null string."
    ::= { tBgpPeerNgEntry 13 }

tBgpPeerNgLocalAddressType       OBJECT-TYPE
    SYNTAX      InetAddressType
    MAX-ACCESS  read-create
    STATUS      current
    DESCRIPTION
        "The value of tBgpPeerNgLocalAddressType specifies the local IP address
         type the peer-group or Peer is to use as advertisement source address.
         tBgpPeerNgLocalAddressType can be either unknown, ipv4 or ipv6."
    ::= { tBgpPeerNgEntry 14 }

tBgpPeerNgLocalAS                OBJECT-TYPE
    SYNTAX      TmnxBgpAutonomousSystem
    MAX-ACCESS  read-create
    STATUS      obsolete
    DESCRIPTION
        "The value of tBgpPeerNgLocalAS specifies the autonomous system number
         to be advertised for this peer.

         If the value of tBgpPeerNgLocalAS, the value of tBgpPeerGroupLocalAS
         or tBgpInstanceLocalAS will be used in that order.

         This object was obsoleted in release 7.0. It is replaced with the
         4-byte AS number defined by tBgpPeerNgLocalAS4Byte."
    DEFVAL      { 0 }
    ::= { tBgpPeerNgEntry 15 }

tBgpPeerNgLocalPreference        OBJECT-TYPE
    SYNTAX      TmnxBgpLocalPreference
    MAX-ACCESS  read-create
    STATUS      current
    DESCRIPTION
        "The value of tBgpPeerNgLocalPreference specifies the default value for
         the Local Preference attribute. This value is used if the BGP route
         arrives from a BGP peer without the Local Preference attribute set.

         It is overridden by any value set via a route policy."
    DEFVAL      { 100 }
    ::= { tBgpPeerNgEntry 16 }

tBgpPeerNgLoopDetect             OBJECT-TYPE
    SYNTAX      BgpLoopDetect
    MAX-ACCESS  read-create
    STATUS      current
    DESCRIPTION
        "The value of tBgpPeerNgLoopDetect determines how the peer session
         should deal with loop detection in the AS Path."
    DEFVAL      { ignore }
    ::= { tBgpPeerNgEntry 17 }

tBgpPeerNgMinRouteAdvertisement  OBJECT-TYPE
    SYNTAX      BgpMinRouteAdvertisement
    UNITS       "seconds"
    MAX-ACCESS  read-create
    STATUS      current
    DESCRIPTION
        "The value of tBgpPeerNgMinRouteAdvertisement specifies the minimum
         interval at which a given path attribute is advertised to a peer."
    DEFVAL      { 30 }
    ::= { tBgpPeerNgEntry 18 }

tBgpPeerNgMaxPrefix              OBJECT-TYPE
    SYNTAX      BgpPrefixLimit
    UNITS       "number of routes"
    MAX-ACCESS  read-create
    STATUS      obsolete
    DESCRIPTION
        "The value of tBgpPeerNgMaxPrefix specifies the maximum number of
         routes that can be learned from this peer.

         A value of zero specifies that there is no limit to the number of
         routes learned.

         The tBgpMaxNgPrefixThreshReached notification is sent when the number
         of routes exceeds a percentage of this limit as specified by
         tBgpPeerNgMaxPrefixThreshold.

         If the number of routes exceeds this limit, then BGP peering will be
         disabled and the tBgpMaxNgPrefix100 notification will be sent.

         An 'inconsistentValue' error is returned if an attempt is made to set
         this object to its default value. This object can be reset by
         resetting appropriate inheritance bit of tBgpPeerNgInheritance.

         This object was obsoleted in release 13.0."
    DEFVAL      { 0 }
    ::= { tBgpPeerNgEntry 19 }

tBgpPeerNgMEDSource              OBJECT-TYPE
    SYNTAX      BgpMEDSource
    MAX-ACCESS  read-create
    STATUS      current
    DESCRIPTION
        "The value of tBgpPeerNgMEDSource specifies the source of the Multi
         Exit Discriminator (MED) value for peers in this group."
    DEFVAL      { noMedOut }
    ::= { tBgpPeerNgEntry 20 }

tBgpPeerNgMEDValue               OBJECT-TYPE
    SYNTAX      BgpMEDValue
    MAX-ACCESS  read-create
    STATUS      current
    DESCRIPTION
        "The value of tBgpPeerNgMEDValue specifies the value of MED when
         tBgpPeerNgMEDSource is 'metricVal'. If the value of
         tBgpPeerNgMEDSource is not 'metricVal', this object is ignored."
    DEFVAL      { 0 }
    ::= { tBgpPeerNgEntry 21 }

tBgpPeerNgMultihop               OBJECT-TYPE
    SYNTAX      BgpTimeToLive
    UNITS       "TTL hops"
    MAX-ACCESS  read-create
    STATUS      current
    DESCRIPTION
        "The value of tBgpPeerNgMultihop specifies the TTL used in IP packet
         header for BGP advertisements.

         Default TTL values for EBGP peer is 1, and MAX_TTL for IBGP peers.
         Default value if not set is  no_type - the peer has to infer its value
         based on local-as, and peer-as in that case."
    DEFVAL      { 0 }
    ::= { tBgpPeerNgEntry 22 }

tBgpPeerNgNextHopSelf            OBJECT-TYPE
    SYNTAX      TruthValue
    MAX-ACCESS  read-create
    STATUS      current
    DESCRIPTION
        "The value of tBgpPeerNgNextHopSelf specifies if routes advertised to
         EBGP peers in this group have NEXTHOP path attribute set to this
         router's physical interface.

         When false, third party routes are advertised."
    DEFVAL      { false }
    ::= { tBgpPeerNgEntry 23 }

tBgpPeerNgNoAggregatorID         OBJECT-TYPE
    SYNTAX      TruthValue
    MAX-ACCESS  read-create
    STATUS      current
    DESCRIPTION
        "The value of tBgpPeerNgNoAggregatorID specifies if different routers
         in the same AS create aggregate routes containing different AS paths.

         A value of 'true' would enable setting the router ID to 0 in the
         aggregator path attribute when BGP is aggregating routes.

         A value of 'false' would disable setting the router ID to 0 in the
         aggregator path attribute when BGP is aggregating routes."
    DEFVAL      { false }
    ::= { tBgpPeerNgEntry 24 }

tBgpPeerNgPassive                OBJECT-TYPE
    SYNTAX      TruthValue
    MAX-ACCESS  read-create
    STATUS      current
    DESCRIPTION
        "The value of tBgpPeerNgPassive specifies if the peer will not attempt
         to connect to the far end peer or just wait for the far end peer to
         connect."
    DEFVAL      { false }
    ::= { tBgpPeerNgEntry 25 }

tBgpPeerNgPeerAS                 OBJECT-TYPE
    SYNTAX      TmnxBgpAutonomousSystem
    MAX-ACCESS  read-create
    STATUS      obsolete
    DESCRIPTION
        "The value of tBgpPeerNgPeerAS specifies the Autonomous System number
         for the remote peer.

         This object was obsoleted in release 7.0.  It is replaced with the
         4-byte AS number defined by tBgpPeerNgPeerAS4Byte."
    DEFVAL      { 0 }
    ::= { tBgpPeerNgEntry 26 }

tBgpPeerNgPeerType               OBJECT-TYPE
    SYNTAX      BgpPeerType
    MAX-ACCESS  read-create
    STATUS      current
    DESCRIPTION
        "The value of tBgpPeerNgPeerType specifies the type of peer -
         noType(1), internal(2) and external(3).

         Default value if not set is noType - the peer has to infer its value
         based on local-as, and peer-as in that case.

         If tBgpPeerNgPeerAS4Byte is set to a non-default value, the value of
         the object tBgpPeerNgPeerType is inferred from tBgpPeerNgPeerAS4Byte
         regardless of the currently set value of tBgpPeerNgPeerType.

         If tBgpPeerNgPeerAS4Byte is set to its default value, the object
         tBgpPeerNgPeerType inherits its value from tBgpPeerGroupPeerAS4Byte."
    DEFVAL      { noType }
    ::= { tBgpPeerNgEntry 27 }

tBgpPeerNgPreference             OBJECT-TYPE
    SYNTAX      TmnxBgpPreference (1..255)
    MAX-ACCESS  read-create
    STATUS      current
    DESCRIPTION
        "The value of tBgpPeerNgPreference specifies the route preference for
         routes learned via the peer."
    DEFVAL      { 170 }
    ::= { tBgpPeerNgEntry 28 }

tBgpPeerNgRemovePrivateAS        OBJECT-TYPE
    SYNTAX      TruthValue
    MAX-ACCESS  read-create
    STATUS      current
    DESCRIPTION
        "The value of tBgpPeerNgRemovePrivateAS specifies if private AS numbers
         should be stripped from the AS Path before advertising them to BGP
         peers."
    DEFVAL      { false }
    ::= { tBgpPeerNgEntry 29 }

tBgpPeerNgLastChanged            OBJECT-TYPE
    SYNTAX      TimeStamp
    MAX-ACCESS  read-only
    STATUS      current
    DESCRIPTION
        "The value tBgpPeerNgLastChanged indicates when an entry in
         tBgpPeerNgTable was last changed."
    ::= { tBgpPeerNgEntry 30 }

tBgpPeerNgInheritance            OBJECT-TYPE
    SYNTAX      Counter64
    MAX-ACCESS  read-create
    STATUS      current
    DESCRIPTION
        "The value of tBgpPeerNgInheritance specifies if the peer entry in this
         row, should inherit the operational value of an object, or use the
         administratively set value.

         This object is a bit-mask, with the following positions:

         tBgpPeerNgShutdown                             0x04
         tBgpPeerNgConnectRetry                         0x10
         tBgpPeerNgHoldTime                             0x20
         tBgpPeerNgKeepAlive                            0x40
         tBgpPeerNgDampening                           0x100
         tBgpPeerNgLocalAddress                        0x200
         tBgpPeerNgLocalAS4Byte                        0x400
         tBgpPeerNgLocalPreference                     0x800
         tBgpPeerNgLoopDetect                         0x1000
         tBgpPeerNgMinRouteAdvertisement              0x2000
         tBgpPeerNgMEDSource                          0x8000
         tBgpPeerNgMEDValue                          0x10000
         tBgpPeerNgMultihop                          0x20000
         tBgpPeerNgNextHopSelf                       0x80000
         tBgpPeerNgNoAggregatorID                   0x100000
         tBgpPeerNgPassive                          0x200000
         tBgpPeerNgPeerAS4Byte                      0x400000
         tBgpPeerNgPeerType                         0x800000
         tBgpPeerNgPreference                      0x1000000
         tBgpPeerNgRemovePrivateAS                 0x2000000
         tBgpPeerNgImportPolicy1                   0x8000000
         tBgpPeerNgExportPolicy1                 0x100000000
         tBgpPeerNgLocalASPrivate               0x2000000000
         tBgpPeerNgMd5Auth                      0x4000000000
         tBgpPeerNgMd5AuthKey                   0x8000000000
         tBgpPeerNgClusterId                   0x10000000000
         tBgpPeerNgDisableClientReflect        0x20000000000
         tBgpPeerNgGracefulRestart             0x40000000000
         tBgpPeerNgGRRestartTime               0x80000000000
         tBgpPeerNgGRStaleRoute               0x100000000000
         tBgpPeerNgGRAdminState               0x200000000000
         tBgpPeerNgFamily                     0x400000000000
         tBgpPeerNgVpnApplyImport             0x800000000000
         tBgpPeerNgVpnApplyExport            0x1000000000000
         tBgpPeerNgASOverride                0x2000000000000
         tBgpPeerNgOrf                       0x4000000000000
         tBgpPeerNgExtCommsOrf               0x8000000000000
         tBgpPeerNgExtCommsSendOrf          0x10000000000000
         tBgpPeerNgExtCommsRecvOrf          0x20000000000000
         tBgpPeerNgLocalAddressType         0x40000000000000
         tBgpPeerNgDisable4ByteASN         0x200000000000000
         tBgpPeerNgHoldTimeIsStrict        0x400000000000000
         tBgpPeerNgL2vpnCiscoInterop       0x800000000000000
         tBgpPeerNgRemovePrivateASLmtd   0x01000000000000000
         tBgpPeerNgDisableCapNegotiation 0x08000000000000000

         These named bits correspond to the names of objects in this table, but
         all import and export policy objects are represented by the same
         tBgpPeerNgImportPolicy1/tBgpPeerNgExportPolicy1 bit.

         When the bit for an object is set to one, then the object's
         administrative and operational value are whatever the DEFVAL or most
         recently SET value is.

         When the bit for an object is set to zero, then the object's
         administrative and operational value are inherited from the
         corresponding object in tBgpPeerGroupTable, or from the corresponding
         object in tBgpInstanceTable."
    DEFVAL      { 0 }
    ::= { tBgpPeerNgEntry 31 }

tBgpPeerNgImportPolicy1          OBJECT-TYPE
    SYNTAX      TPolicyStatementNameOrEmpty
    MAX-ACCESS  read-create
    STATUS      obsolete
    DESCRIPTION
        "The value of tBgpPeerNgImportPolicy1 specifies import policy number 1
         for peer level.

         This object was obsoleted in release 10.0. It is replaced by object
         tBgpPeerPlcyImportPolicy1."
    DEFVAL      { ''H }
    ::= { tBgpPeerNgEntry 32 }

tBgpPeerNgImportPolicy2          OBJECT-TYPE
    SYNTAX      TPolicyStatementNameOrEmpty
    MAX-ACCESS  read-create
    STATUS      obsolete
    DESCRIPTION
        "The value of tBgpPeerNgImportPolicy2 specifies import policy number 2
         for peer level.

         This object was obsoleted in release 10.0. It is replaced by object
         tBgpPeerPlcyImportPolicy2."
    DEFVAL      { ''H }
    ::= { tBgpPeerNgEntry 33 }

tBgpPeerNgImportPolicy3          OBJECT-TYPE
    SYNTAX      TPolicyStatementNameOrEmpty
    MAX-ACCESS  read-create
    STATUS      obsolete
    DESCRIPTION
        "The value of tBgpPeerNgImportPolicy3 specifies import policy number 3
         for peer level.

         This object was obsoleted in release 10.0. It is replaced by object
         tBgpPeerPlcyImportPolicy3."
    DEFVAL      { ''H }
    ::= { tBgpPeerNgEntry 34 }

tBgpPeerNgImportPolicy4          OBJECT-TYPE
    SYNTAX      TPolicyStatementNameOrEmpty
    MAX-ACCESS  read-create
    STATUS      obsolete
    DESCRIPTION
        "The value of tBgpPeerNgImportPolicy4 specifies import policy number 4
         for peer level.

         This object was obsoleted in release 10.0. It is replaced by object
         tBgpPeerPlcyImportPolicy4."
    DEFVAL      { ''H }
    ::= { tBgpPeerNgEntry 35 }

tBgpPeerNgImportPolicy5          OBJECT-TYPE
    SYNTAX      TPolicyStatementNameOrEmpty
    MAX-ACCESS  read-create
    STATUS      obsolete
    DESCRIPTION
        "The value of tBgpPeerNgImportPolicy5 specifies import policy number 5
         for peer level.

         This object was obsoleted in release 10.0. It is replaced by object
         tBgpPeerPlcyImportPolicy5."
    DEFVAL      { ''H }
    ::= { tBgpPeerNgEntry 36 }

tBgpPeerNgExportPolicy1          OBJECT-TYPE
    SYNTAX      TPolicyStatementNameOrEmpty
    MAX-ACCESS  read-create
    STATUS      obsolete
    DESCRIPTION
        "The value of tBgpPeerNgExportPolicy1 specifies export policy number 1
         for peer level.

         This object was obsoleted in release 10.0. It is replaced by object
         tBgpPeerPlcyExportPolicy1."
    DEFVAL      { ''H }
    ::= { tBgpPeerNgEntry 37 }

tBgpPeerNgExportPolicy2          OBJECT-TYPE
    SYNTAX      TPolicyStatementNameOrEmpty
    MAX-ACCESS  read-create
    STATUS      obsolete
    DESCRIPTION
        "The value of tBgpPeerNgExportPolicy2 specifies export policy number 2
         for peer level.

         This object was obsoleted in release 10.0. It is replaced by object
         tBgpPeerPlcyExportPolicy2."
    DEFVAL      { ''H }
    ::= { tBgpPeerNgEntry 38 }

tBgpPeerNgExportPolicy3          OBJECT-TYPE
    SYNTAX      TPolicyStatementNameOrEmpty
    MAX-ACCESS  read-create
    STATUS      obsolete
    DESCRIPTION
        "The value of tBgpPeerNgExportPolicy3 specifies export policy number 3
         for peer level.

         This object was obsoleted in release 10.0. It is replaced by object
         tBgpPeerPlcyExportPolicy3."
    DEFVAL      { ''H }
    ::= { tBgpPeerNgEntry 39 }

tBgpPeerNgExportPolicy4          OBJECT-TYPE
    SYNTAX      TPolicyStatementNameOrEmpty
    MAX-ACCESS  read-create
    STATUS      obsolete
    DESCRIPTION
        "The value of tBgpPeerNgExportPolicy4 specifies export policy number 4
         for peer level.

         This object was obsoleted in release 10.0. It is replaced by object
         tBgpPeerPlcyExportPolicy4."
    DEFVAL      { ''H }
    ::= { tBgpPeerNgEntry 40 }

tBgpPeerNgExportPolicy5          OBJECT-TYPE
    SYNTAX      TPolicyStatementNameOrEmpty
    MAX-ACCESS  read-create
    STATUS      obsolete
    DESCRIPTION
        "The value of tBgpPeerNgExportPolicy5 specifies export policy number 5
         for peer level.

         This object was obsoleted in release 10.0. It is replaced by object
         tBgpPeerPlcyExportPolicy5."
    DEFVAL      { ''H }
    ::= { tBgpPeerNgEntry 41 }

tBgpPeerNgOperStatus             OBJECT-TYPE
    SYNTAX      BgpOperState
    MAX-ACCESS  read-only
    STATUS      current
    DESCRIPTION
        "The value of tBgpPeerNgOperStatus indicates the operational status of
         this BGP Peer.

         A value of 'inService(2)' means the bgp peer is fully functional.

         A value of 'outOfService(3)' means the bgp peer is down.

         A value of 'transition(4)' means the bgp peer is performing a
         transition from state inService(2) to outOfService(3) or vice versa.

         A value of 'disabled(5)' means the BGP peer needs to be restarted by
         the user."
    ::= { tBgpPeerNgEntry 42 }

tBgpPeerNgLocalASPrivate         OBJECT-TYPE
    SYNTAX      TruthValue
    MAX-ACCESS  read-create
    STATUS      current
    DESCRIPTION
        "The value of tBgpPeerNgLocalASPrivate specifies if the local
         autonomous system number is hidden in paths learned from peering.

         When the value of tBgpPeerNgLocalAS4Byte is changed, the value of
         tBgpPeerNgLocalASPrivate is reset to its default value.

         An 'inconsistentValue' error is returned if an attempt is made to set
         this object to a non-default value when the value of object
         tBgpPeerNgLocalAS4Byte is not set to non-default value."
    DEFVAL      { false }
    ::= { tBgpPeerNgEntry 43 }

tBgpPeerNgMd5Auth                OBJECT-TYPE
    SYNTAX      TruthValue
    MAX-ACCESS  read-create
    STATUS      current
    DESCRIPTION
        "The value of tBgpPeerNgMd5Auth specifies if the authentication using
         MD5 message based digest protocol is enabled."
    DEFVAL      { false }
    ::= { tBgpPeerNgEntry 44 }

tBgpPeerNgMd5AuthKey             OBJECT-TYPE
    SYNTAX      DisplayString (SIZE (0..255))
    MAX-ACCESS  read-create
    STATUS      current
    DESCRIPTION
        "The value of tBgpPeerNgMd5AuthKey specifies the authentication key to
         be used between BGP peers neighbors before establishing sessions.

         Authentication is done using the MD5 message based digest protocol.

         Authentication can be configured globally and applied to all BGP peers
         or per group or per peer. The most specific value is used.

         The authentication key can be any combination of letters or numbers.
         Note that the string CANNOT contain embedded nulls."
    DEFVAL      { ''H }
    ::= { tBgpPeerNgEntry 45 }

tBgpPeerNgClusterId              OBJECT-TYPE
    SYNTAX      IpAddress
    MAX-ACCESS  read-create
    STATUS      current
    DESCRIPTION
        "This value of tBgpPeerNgClusterId specifies the cluster ID for a route
         reflector server.

         A value of 0.0.0.0 indicates that no cluster ID has been assigned to
         the BGP peer."
    DEFVAL      { '00000000'H }
    ::= { tBgpPeerNgEntry 46 }

tBgpPeerNgDisableClientReflect   OBJECT-TYPE
    SYNTAX      TruthValue
    MAX-ACCESS  read-create
    STATUS      current
    DESCRIPTION
        "The value of tBgpPeerNgDisableClientReflect specifies if reflection of
         routes by the route reflector to all client peers within its cluster
         is enabled or disabled.

         A value of 'false' means reflection of routes to all client peers is
         enabled."
    DEFVAL      { false }
    ::= { tBgpPeerNgEntry 47 }

tBgpPeerNgGracefulRestart        OBJECT-TYPE
    SYNTAX      TruthValue
    MAX-ACCESS  read-create
    STATUS      current
    DESCRIPTION
        "The value of tBgpPeerNgGracefulRestart specifies whether or not
         graceful restart capabilities are enabled on this instance of BGP.

         When the value is set to 'false' graceful restart is disabled and any
         previous configuration of other graceful restart parameters is
         removed."
    DEFVAL      { false }
    ::= { tBgpPeerNgEntry 48 }

tBgpPeerNgGRRestartTime          OBJECT-TYPE
    SYNTAX      Unsigned32 (0..4095)
    UNITS       "seconds"
    MAX-ACCESS  read-create
    STATUS      current
    DESCRIPTION
        "The value of tBgpPeerNgGRRestartTime specifies the maximum amount of
         time in seconds that a graceful restart should take."
    DEFVAL      { 300 }
    ::= { tBgpPeerNgEntry 49 }

tBgpPeerNgGRStaleRoute           OBJECT-TYPE
    SYNTAX      Unsigned32 (1..3600)
    UNITS       "seconds"
    MAX-ACCESS  read-create
    STATUS      current
    DESCRIPTION
        "The value of tBgpPeerNgGRStaleRoute specifies the maximum
         amount of time in seconds that stale routes should be maintained
         after a graceful restart is initiated.  This value should be
         at least as large a the value of tBgpPeerNgGRRestartTime."
    DEFVAL      { 360 }
    ::= { tBgpPeerNgEntry 50 }

tBgpPeerNgGRAdminState           OBJECT-TYPE
    SYNTAX      TmnxAdminState
    MAX-ACCESS  read-create
    STATUS      current
    DESCRIPTION
        "The value of tBgpPeerNgGRAdminState specifies the desired
         administrative state of the graceful restart capabilities for
         this peer of the BGP protocol.  When the value is 'outOfService'
         the graceful restart capabilities are disabled but the
         graceful restart configuration parameters are retained."
    DEFVAL      { inService }
    ::= { tBgpPeerNgEntry 51 }

tBgpPeerNgGROperState            OBJECT-TYPE
    SYNTAX      TmnxOperState
    MAX-ACCESS  read-only
    STATUS      current
    DESCRIPTION
        "The value of tBgpPeerNgGROperState indicates the operational status of
         the graceful restart capabilities for this peer of the BGP protocol."
    ::= { tBgpPeerNgEntry 52 }

tBgpPeerNgFamily                 OBJECT-TYPE
    SYNTAX      TmnxIpFamily
    MAX-ACCESS  read-create
    STATUS      current
    DESCRIPTION
        "The value of tBgpPeerNgFamily specifies the types of routing
         information to be distributed by the local side of this Peer of
         the BGP protocol.  BGP was initially designed for the distribution
         of IPv4 routing information.  Multi-protocol extensions and the
         use of a VPN-IPv4, VPN-IPv6, MVPN-IPv4 and L2-VPN address have been
         added to extend its ability to carry overlapping routing information.

         A 'vpnIpv4 (2)' address is a 12-byte value consisting of
         the 8-byte route distinguisher, RD, and the 4-byte ipv4 IP address
         prefix.  The RD must be unique within the scope of the VPRN.
         This allows the IP address prefixes within different VRFs to
         overlap.

         'ipv6 (3)', 'mcastIpv4 (4)', 'l2vpn (6)' and 'mcastVpnIpv4 (12)' are
         multi-protocol extensions to BGP.

         'mcastIpv6 (16)' is part of multi-protocol extension to BGP.

         A 'vpnIpv6 (5)' address is a 24-byte value consisting of the 8-byte
         RD, and 16 bytes for the IPv6 address. When both IPv4 and IPv6 VPRN
         services are enabled, the PE router uses the same RD for both address
         families.

         A 'l2vpn (6)' address is a 12-byte Virtual Switch Instance identifier
         (VSI-ID) value consisting of the 8-byte route distinguisher(RD)
         followed by a 4-byte value.

         A 'mvpnIpv4  (7)' address is variable size value consisting of the
         1-byte route type, 1-byte length and variable size route type specific.
         Route type defines encoding for the route type specific field. Length
         indicates the length in octets of the route type specific field.

         A 'mdtSafi (8)' address is a 16-byte value consisting of 12-byte route
         distinguisher(RD) followed by a 4-byte group address.

         A 'mspw (9)' address is a dynamic multi-segment pseudowire address.

         A 'flowIpv4 (10)' address is a variable size value consisting of 1 or
         2-byte NLRI(Network Layer Reachability Information) length followed by
         a variable length NLRI value.

         A 'routeTarget (11)' address is a variable size value consisting of
         zero length or 12 byte (ipv4) or 24 byte (ipv6) NLRI (Network Layer
         Reachability Information) length followed by a variable length NLRI
         value.

         A 'mvpnIpv6 (13)' address is variable size value consisting of the
         1-byte route type, 1-byte length and variable size route type
         specific. Route type defines encoding for the route type specific
         field. Length indicates the length in octets of the route type
         specific field.

         A 'flowIpv6 (14)' address is a variable size value consisting of 1 or
         2-byte NLRI(Network Layer Reachability Information) length followed by
         a variable length NLRI value.

         A 'evpn (15)' address is variable size value consisting of the 1-byte
         route type, 1-byte length and variable size route type specific. Route
         type defines encoding for the route type specific field. Length
         indicates the length in octets of the route type specific field."
    DEFVAL      { {ipv4} }
    ::= { tBgpPeerNgEntry 53 }

tBgpPeerNgVpnRemoteFamily        OBJECT-TYPE
    SYNTAX      TmnxIpFamily
    MAX-ACCESS  read-only
    STATUS      current
    DESCRIPTION
        "The value of tBgpPeerNgVpnRemoteFamily indicates the types of routing
         information to be distributed by the remote end of this Peer of the
         BGP protocol.  BGP was initially designed for the distribution of
         IPv4 routing information.  Multi-protocol extensions and the use
         of a VPN-IPv4,VPN-IPv6, MVPN-IPv4 and L2-VPN address have been added to
         extend its ability to carry overlapping routing information.

         A 'vpnIpv4 (2)' address is a 12-byte value consisting of
         the 8-byte route distinguisher, RD, and the 4-byte ipv4 IP address
         prefix.  The RD must be unique within the scope of the VPRN.
         This allows the IP address prefixes within different VRFs to
         overlap.

         'ipv6 (3)', 'mcastIpv4 (4)', and 'l2vpn (6)' are multi-protocol
         extensions to BGP.


         'mcastIpv6 (16)' is part of multi-protocol extension to BGP.

         A 'vpnIpv6 (5)' address is a 24-byte value consisting of the 8-byte
         RD, and 16 bytes for the IPv6 address. When both IPv4 and IPv6 VPRN
         services are enabled, the PE router uses the same RD for both address
         families.

         A 'l2vpn (6)' address is a 12-byte Virtual Switch Instance identifier
         (VSI-ID) value consisting of the 8-byte route distinguisher(RD)
         followed by a 4-byte value.

         A 'mvpnIpv4  (7)' address is variable size value consisting of the
         1-byte route type, 1-byte length and variable size route type specific.
         Route type defines encoding for the route type specific field. Length
         indicates the length in octets of the route type specific field."
    ::= { tBgpPeerNgEntry 54 }

tBgpPeerNgVpnApplyImport         OBJECT-TYPE
    SYNTAX      TruthValue
    MAX-ACCESS  read-create
    STATUS      current
    DESCRIPTION
        "The value of tBgpPeerNgVpnApplyImport specifies if the BGP import
         route policies are applied to VPN-IPv4 routes of this group.

         When the value is 'false' the application of the base instance BGP
         import route policies to VPN-IPv4 routes of this group is disabled."
    DEFVAL      { false }
    ::= { tBgpPeerNgEntry 55 }

tBgpPeerNgVpnApplyExport         OBJECT-TYPE
    SYNTAX      TruthValue
    MAX-ACCESS  read-create
    STATUS      current
    DESCRIPTION
        "The value of tBgpPeerNgVpnApplyExport specifies if the BGP export
         route policies are applied to VPN-IPv4 routes of this group.

         When the value is 'false' the application of the BGP export route
         policies to VPN-IPv4 routes of this group is disabled."
    DEFVAL      { false }
    ::= { tBgpPeerNgEntry 56 }

tBgpPeerNgVpnLocalCaps           OBJECT-TYPE
    SYNTAX      TmnxVpnCapability
    MAX-ACCESS  read-only
    STATUS      current
    DESCRIPTION
        "The value of tBgpPeerNgVpnLocalCaps indicates the capabilities
         supported on the local end of the BGP Peer."
    ::= { tBgpPeerNgEntry 57 }

tBgpPeerNgVpnRemoteCaps          OBJECT-TYPE
    SYNTAX      TmnxVpnCapability
    MAX-ACCESS  read-only
    STATUS      current
    DESCRIPTION
        "The value of tBgpPeerNgVpnRemoteCaps indicates the capabilities
         advertised by the remote end of the BGP Peer."
    ::= { tBgpPeerNgEntry 58 }

tBgpPeerNgConnState              OBJECT-TYPE
    SYNTAX      INTEGER {
        idle        (1),
        connect     (2),
        active      (3),
        opensent    (4),
        openconfirm (5),
        established (6)
    }
    MAX-ACCESS  read-only
    STATUS      current
    DESCRIPTION
        "The value of tBgpPeerNgConnState indicates the BGP peer connection
         state.

         This object is the shadow object of bgpPeerState as existing in the
         BGP4-MIB."
    ::= { tBgpPeerNgEntry 59 }

tBgpPeerNgASOverride             OBJECT-TYPE
    SYNTAX      TruthValue
    MAX-ACCESS  read-create
    STATUS      current
    DESCRIPTION
        "The value of tBgpPeerNgASOverride specifies if the service provider
         BGP will override the customer AS number in the ASPATH with its own AS
         number.

         A value of 'true' means the service provider BGP will override the
         customer AS number in the ASPATH with its own AS number.

         Without this feature there could be scenarios where multiple CE
         locations belonging to the same AS will not be able to communicate due
         to a potential loop detection."
    DEFVAL      { false }
    ::= { tBgpPeerNgEntry 60 }

tBgpPeerNgOrf                    OBJECT-TYPE
    SYNTAX      TruthValue
    MAX-ACCESS  read-create
    STATUS      current
    DESCRIPTION
        "The value of tBgpPeerNgOrf specifies if outbound route filtering
         capability is enabled or disabled for the BGP peer."
    DEFVAL      { false }
    ::= { tBgpPeerNgEntry 61 }

tBgpPeerNgExtCommsOrf            OBJECT-TYPE
    SYNTAX      TruthValue
    MAX-ACCESS  read-create
    STATUS      current
    DESCRIPTION
        "The value of tBgpPeerNgExtCommsOrf specifies if outbound route
         filtering capability is based on extended communities for the BGP
         peer."
    DEFVAL      { false }
    ::= { tBgpPeerNgEntry 62 }

tBgpPeerNgExtCommsSendOrf        OBJECT-TYPE
    SYNTAX      TruthValue
    MAX-ACCESS  read-create
    STATUS      current
    DESCRIPTION
        "The value of tBgpPeerNgExtCommsSendOrf specifies if outbound route
         filter advertisement to the neighbors in this BGP peer."
    DEFVAL      { false }
    ::= { tBgpPeerNgEntry 63 }

tBgpPeerNgExtCommsRecvOrf        OBJECT-TYPE
    SYNTAX      TruthValue
    MAX-ACCESS  read-create
    STATUS      current
    DESCRIPTION
        "The value of tBgpPeerNgExtCommsRecvOrf specifies if outbound route
         filter for this BGP peer is accepted from the neighbors is enabled."
    DEFVAL      { false }
    ::= { tBgpPeerNgEntry 64 }

tBgpPeerNgLocalAS4Byte           OBJECT-TYPE
    SYNTAX      InetAutonomousSystemNumber
    MAX-ACCESS  read-create
    STATUS      current
    DESCRIPTION
        "The value of tBgpPeerNgLocalAS4Byte specifies the autonomous system
         number to be advertised to this peer."
    DEFVAL      { 0 }
    ::= { tBgpPeerNgEntry 65 }

tBgpPeerNgPeerAS4Byte            OBJECT-TYPE
    SYNTAX      InetAutonomousSystemNumber
    MAX-ACCESS  read-create
    STATUS      current
    DESCRIPTION
        "The value of tBgpPeerNgPeerAS4Byte specifies the autonomous system
         number for the remote peer."
    DEFVAL      { 0 }
    ::= { tBgpPeerNgEntry 66 }

tBgpPeerNgDisable4ByteASN        OBJECT-TYPE
    SYNTAX      TruthValue
    MAX-ACCESS  read-create
    STATUS      current
    DESCRIPTION
        "The value of tBgpPeerNgDisable4ByteASN specifies whether or not 4-byte
         ASN capability will be advertised by this peer.

         When the value of tBgpPeerNgDisable4ByteASN is set to false, 4-byte
         ASN support will be negotiated with the associated remote peers. When
         the value of tBgpPeerNgDisable4ByteASN is set to true, 4-byte ASN
         capability will not be advertised by this peer."
    DEFVAL      { false }
    ::= { tBgpPeerNgEntry 67 }

tBgpPeerNgHoldTimeIsStrict       OBJECT-TYPE
    SYNTAX      TruthValue
    MAX-ACCESS  read-create
    STATUS      obsolete
    DESCRIPTION
        "The value of tBgpPeerNgHoldTimeIsStrict specifies whether or not
         tBgpPeerNgHoldTime has to be strictly enforced.

         When the value of tBgpPeerNgHoldTimeIsStrict is true, BGP on this peer
         will not negotiate a hold time lower than the configured value for
         tBgpPeerNgHoldTime.

         This object is obsoleted in release 10.0. Desired functionality of
         strict enforcement of hold time can be achieved by configuring the
         value of tBgpPeerNgMinHoldTime."
    DEFVAL      { false }
    ::= { tBgpPeerNgEntry 68 }

tBgpPeerNgL2vpnCiscoInterop      OBJECT-TYPE
    SYNTAX      TruthValue
    MAX-ACCESS  read-create
    STATUS      current
    DESCRIPTION
        "The value of tBgpPeerNgL2vpnCiscoInterop specifies whether BGP will
         provide translation between non-compliant NLRI formats of Cisco.

         BGP Peer sessions must be manually configured towards the
         non-compliant Cisco PEs.

         When the value of tBgpPeerNgL2vpnCiscoInterop is 'true', Cisco
         non-compliant NLRI format will be used; one byte length field instead
         of two bytes for BGP NLRI.

         When the value of tBgpPeerNgL2vpnCiscoInterop is 'false', Cisco
         non-compliant NLRI format will not be used or supported."
    DEFVAL      { false }
    ::= { tBgpPeerNgEntry 69 }

tBgpPeerNgRemovePrivateASLmtd    OBJECT-TYPE
    SYNTAX      TruthValue
    MAX-ACCESS  read-create
    STATUS      current
    DESCRIPTION
        "The value of tBgpPeerNgRemovePrivateASLmtd specifies whether BGP will
         remove the private AS numbers for this peer.

         When the value of tBgpPeerNgRemovePrivateASLmtd is true, BGP will
         remove private AS numbers from the AS Path for this peer.

         When the value of tBgpPeerNgRemovePrivateAS is changed, the value of
         tBgpPeerNgRemovePrivateASLmtd is reset to its default value.

         An 'inconsistentValue' error is returned if an attempt is made to set
         this object to its default value. This object can be reset by
         resetting appropriate inheritance bit of tBgpPeerNgInheritance."
    DEFVAL      { false }
    ::= { tBgpPeerNgEntry 70 }

tBgpPeerNgMaxPrefixLogOnly       OBJECT-TYPE
    SYNTAX      TruthValue
    MAX-ACCESS  read-create
    STATUS      obsolete
    DESCRIPTION
        "The value of tBgpPeerNgMaxPrefixLogOnly specifies whether BGP peering
         will be disabled when tBgpPeerGroupMaxPrefix is exceeded.

         When the value is set to 'true', BGP peering will be enabled.

         When the value is set to 'false', BGP peering will be disabled.

         This object was obsoleted in release 13.0."
    DEFVAL      { false }
    ::= { tBgpPeerNgEntry 71 }

tBgpPeerNgMaxPrefixThreshold     OBJECT-TYPE
    SYNTAX      Unsigned32 (1..100)
    UNITS       "percent"
    MAX-ACCESS  read-create
    STATUS      obsolete
    DESCRIPTION
        "The value of tBgpPeerNgMaxPrefixThreshold specifies a percentage of
         tBgpPeerNgMaxPrefix.

         This object was obsoleted in release 13.0."
    DEFVAL      { 90 }
    ::= { tBgpPeerNgEntry 72 }

tBgpPeerNgDisableCapNegotiation  OBJECT-TYPE
    SYNTAX      TruthValue
    MAX-ACCESS  read-create
    STATUS      current
    DESCRIPTION
        "The value of tBgpPeerNgDisableCapNegotiation specifies whether
         capability negotiation is disabled for this peer."
    DEFVAL      { false }
    ::= { tBgpPeerNgEntry 73 }

tBgpPeerNgCreationType           OBJECT-TYPE
    SYNTAX      INTEGER {
        static          (1),
        dynamic         (2),
        dynamicIfRemote (3),
        dynamicIfLocal  (4)
    }
    MAX-ACCESS  read-create
    STATUS      current
    DESCRIPTION
        "The value of tBgpPeerNgCreationType specifies the way in which the
         peer was created.

         If the value of tBgpPeerNgCreationType is 'static', the peer was
         created statically.

         If the value of tBgpPeerNgCreationType is 'dynamic', the peer was
         created when the remote BGP speaker established a connection that
         matches a dynamic-peer prefix.

         If the value of tBgpPeerNgCreationType is 'dynamicIfRemote', the peer
         was created by an incoming OPEN matching a dynamic peer interface.

         If the value of tBgpPeerNgCreationType is 'dynamicIfLocal', the peer
         was created by receiving a router-advertisement on a dynamic peer
         interface."
    DEFVAL      { static }
    ::= { tBgpPeerNgEntry 74 }

tBgpPeerNgOperTable              OBJECT-TYPE
    SYNTAX      SEQUENCE OF TBgpPeerNgOperEntry
    MAX-ACCESS  not-accessible
    STATUS      current
    DESCRIPTION
        "The tBgpPeerNgOperTable is the list of configured BGP Peers and their
         operational status information."
    ::= { tBgpPeerObjects 8 }

tBgpPeerNgOperEntry              OBJECT-TYPE
    SYNTAX      TBgpPeerNgOperEntry
    MAX-ACCESS  not-accessible
    STATUS      current
    DESCRIPTION
        "Defines an entry (conceptual row) in the tBgpPeerNgOperTable.

         Entries in tBgpPeerNgOperTable are created when entries are created in
         tBgpPeerNgTable."
    AUGMENTS    { tBgpPeerNgEntry }
    ::= { tBgpPeerNgOperTable 1 }

TBgpPeerNgOperEntry              ::= SEQUENCE
{
    tBgpPeerNgOperMsgOctetsRcvd      Counter64,
    tBgpPeerNgOperMsgOctetsSent      Counter64,
    tBgpPeerNgOperInputQueueMsgs     Gauge32,
    tBgpPeerNgOperOutputQueueMsgs    Gauge32,
    tBgpPeerNgOperReceivedPrefixes   Counter32,
    tBgpPeerNgOperSentPrefixes       Counter32,
    tBgpPeerNgOperActivePrefixes     Gauge32,
    tBgpPeerNgOperReceivedPaths      Counter32,
    tBgpPeerNgOperPathsSupByDamping  Counter32,
    tBgpPeerNgOperFlaps              Counter32,
    tBgpPeerNgOperLastState          BgpPeerState,
    tBgpPeerNgOperLastEvent          BgpPeerEvent,
    tBgpPeerNgOperVpnRecvPrefixes    Counter32,
    tBgpPeerNgOperVpnSentPrefixes    Counter32,
    tBgpPeerNgOperVpnActivePrefixes  Gauge32,
    tBgpPeerNgOperGRSupport          TruthValue,
    tBgpPeerNgOperGRFamilyRestart    TmnxBGPFamilyType,
    tBgpPeerNgOperGRFamilyFwding     TmnxBGPFamilyType,
    tBgpPeerNgOperGRFamilyNegotiated TmnxBGPFamilyType,
    tBgpPeerNgOperGRRecvEOR          TmnxBGPFamilyType,
    tBgpPeerNgOperGRSendEOR          TmnxBGPFamilyType,
    tBgpPeerNgOperGRStaleRoutesTime  Unsigned32,
    tBgpPeerNgOperGRReqRestartTime   Unsigned32,
    tBgpPeerNgOperGRStatus           INTEGER,
    tBgpPeerNgOperNumRestarts        Unsigned32,
    tBgpPeerNgOperLastRestartTime    TimeStamp,
    tBgpPeerNgOperV6ReceivedPrefixes Counter32,
    tBgpPeerNgOperV6SentPrefixes     Counter32,
    tBgpPeerNgOperV6ActivePrefixes   Gauge32,
    tBgpPeerNgOperV6ReceivedPaths    Counter32,
    tBgpPeerNgOperV6SuppPathsDamping Counter32,
    tBgpPeerNgOperVpnReceivedPaths   Counter32,
    tBgpPeerNgOperV4SuppPfxDamp      Counter32,
    tBgpPeerNgOperVpnSuppPfxDamp     Counter32,
    tBgpPeerNgOperV6SuppPfxDamp      Counter32,
    tBgpPeerNgOperMCastV4SuppPfxDamp Counter32,
    tBgpPeerNgOperMCastV4RecvPfxs    Counter32,
    tBgpPeerNgOperMCastV4SentPfxs    Counter32,
    tBgpPeerNgOperMCastV4ActivePfxs  Counter32,
    tBgpPeerNgOperVpnIpv6RecvPfxs    Counter32,
    tBgpPeerNgOperVpnIpv6SentPfxs    Counter32,
    tBgpPeerNgOperVpnIpv6ActivePfxs  Gauge32,
    tBgpPeerNgOperVpnIpv6SuppPfxDamp Counter32,
    tBgpPeerNgOperMvpnV4SuppPfxDamp  Counter32,
    tBgpPeerNgOperMvpnV4RecvPfxs     Counter32,
    tBgpPeerNgOperMvpnV4SentPfxs     Counter32,
    tBgpPeerNgOperMvpnV4ActivePfxs   Counter32,
    tBgpPeerNgOperl2VpnSuppPfxDamp   Counter32,
    tBgpPeerNgOperl2VpnRecvPfxs      Counter32,
    tBgpPeerNgOperl2VpnSentPfxs      Counter32,
    tBgpPeerNgOperl2VpnActivePfxs    Counter32,
    tBgpPeerNgOperMdtSafiSuppPfxDamp Counter32,
    tBgpPeerNgOperMdtSafiRecvPfxs    Counter32,
    tBgpPeerNgOperMdtSafiSentPfxs    Counter32,
    tBgpPeerNgOperMdtSafiActivePfxs  Counter32,
    tBgpPeerNgOperMsPwSuppPfxDamp    Counter32,
    tBgpPeerNgOperMsPwRecvPfxs       Counter32,
    tBgpPeerNgOperMsPwSentPfxs       Counter32,
    tBgpPeerNgOperMsPwActivePfxs     Counter32,
    tBgpPeerNgOperFlowIpv4SupPfxDamp Counter32,
    tBgpPeerNgOperFlowIpv4RecvPfxs   Counter32,
    tBgpPeerNgOperFlowIpv4SentPfxs   Counter32,
    tBgpPeerNgOperFlowIpv4ActivePfxs Counter32,
    tBgpPeerNgAddPathSendRemoteCaps  TmnxAddPathAddressFamily,
    tBgpPeerNgAddPathRecvRemoteCaps  TmnxAddPathAddressFamily,
    tBgpPeerNgOperBackupPrefixes     Counter32,
    tBgpPeerNgOperV6BackupPrefixes   Counter32,
    tBgpPeerNgOperRtTgtSuppPfxDamp   Counter32,
    tBgpPeerNgOperRtTgtRecvPfxs      Counter32,
    tBgpPeerNgOperRtTgtSentPfxs      Counter32,
    tBgpPeerNgOperRtTgtActivePfxs    Counter32,
    tBgpPeerNgOperVpnV4BackupPfxs    Counter32,
    tBgpPeerNgOperVpnV6BackupPfxs    Counter32,
    tBgpPeerNgOperMcastVpnV4RecvPfxs Counter32,
    tBgpPeerNgOperMcastVpnV4SentPfxs Counter32,
    tBgpPeerNgOperMcastVpnV4ActPfxs  Counter32,
    tBgpPeerNgOperMvpnV6SuppPfxDamp  Counter32,
    tBgpPeerNgOperMvpnV6RecvPfxs     Counter32,
    tBgpPeerNgOperMvpnV6SentPfxs     Counter32,
    tBgpPeerNgOperMvpnV6ActivePfxs   Counter32,
    tBgpPeerNgOperFlowIpv6SupPfxDamp Counter32,
    tBgpPeerNgOperFlowIpv6RecvPfxs   Counter32,
    tBgpPeerNgOperFlowIpv6SentPfxs   Counter32,
    tBgpPeerNgOperFlowIpv6ActivePfxs Counter32,
    tBgpPeerNgOperEvpnSupPfxDamp     Counter32,
    tBgpPeerNgOperEvpnRecvPfxs       Counter32,
    tBgpPeerNgOperEvpnSentPfxs       Counter32,
    tBgpPeerNgOperEvpnActivePfxs     Counter32,
    tBgpPeerNgOperUpdateErrors       Counter32,
    tBgpPeerNgOperGRNotifFamilyNego  TmnxBGPFamilyType,
    tBgpPeerNgOperRemIdleHoldTime    Unsigned32,
    tBgpPeerNgOperMcastV6SupPfxDamp  Counter32,
    tBgpPeerNgOperMcastV6RecvPfxs    Counter32,
    tBgpPeerNgOperMcastV6SentPfxs    Counter32,
    tBgpPeerNgOperMcastV6ActivePfxs  Counter32,
    tBgpPeerNgOperIpv4RejPfxs        Counter32,
    tBgpPeerNgOperVpnIpv4RejPfxs     Counter32,
    tBgpPeerNgOperIpv6RejPfxs        Counter32,
    tBgpPeerNgOperVpnIpv6RejPfxs     Counter32,
    tBgpPeerNgOperMCastV4RejPfxs     Counter32,
    tBgpPeerNgOperl2VpnRejPfxs       Counter32,
    tBgpPeerNgOperMvpnV4RejPfxs      Counter32,
    tBgpPeerNgOperMdtSafiRejPfxs     Counter32,
    tBgpPeerNgOperMsPwRejPfxs        Counter32,
    tBgpPeerNgOperFlowIpv4RejPfxs    Counter32,
    tBgpPeerNgOperRtTgtRejPfxs       Counter32,
    tBgpPeerNgOperMcastVpnV4RejPfxs  Counter32,
    tBgpPeerNgOperMvpnV6RejPfxs      Counter32,
    tBgpPeerNgOperFlowIpv6RejPfxs    Counter32,
    tBgpPeerNgOperEvpnRejPfxs        Counter32,
    tBgpPeerNgOperMCastV6RejPfxs     Counter32,
    tBgpPeerNgOperMcVpnV4SuppPfxDamp Counter32,
    tBgpPeerNgOperLabelV4SupPfxDamp  Counter32,
    tBgpPeerNgOperLabelV4RecvPfxs    Counter32,
    tBgpPeerNgOperLabelV4SentPfxs    Counter32,
    tBgpPeerNgOperLabelV4ActivePfxs  Counter32,
    tBgpPeerNgOperLabelV4RejPfxs     Counter32,
    tBgpPeerNgOperLabelV4BackupPfxs  Counter32,
    tBgpPeerNgOperLabelV6SupPfxDamp  Counter32,
    tBgpPeerNgOperLabelV6RecvPfxs    Counter32,
    tBgpPeerNgOperLabelV6SentPfxs    Counter32,
    tBgpPeerNgOperLabelV6ActivePfxs  Counter32,
    tBgpPeerNgOperLabelV6RejPfxs     Counter32,
    tBgpPeerNgOperLabelV6BackupPfxs  Counter32,
    tBgpPeerNgOperBgpLsSupPfxDamp    Counter32,
    tBgpPeerNgOperBgpLsRecvPfxs      Counter32,
    tBgpPeerNgOperBgpLsSentPfxs      Counter32,
    tBgpPeerNgOperBgpLsActivePfxs    Counter32,
    tBgpPeerNgOperBgpLsRejPfxs       Counter32,
    tBgpPeerNgOperMcastVpnV6RecvPfxs Counter32,
    tBgpPeerNgOperMcastVpnV6ActPfxs  Counter32,
    tBgpPeerNgOperMcastVpnV6RejPfxs  Counter32,
    tBgpPeerNgOperMcastVpnV6SentPfxs Counter32,
    tBgpPeerNgOperMcVpnV6SuppPfxDamp Counter32,
    tBgpPeerOperLLGRSupported        TruthValue,
    tBgpPeerOperLLGRFamilySupported  TmnxBGPFamilyType,
    tBgpPeerOperLLGRFamilyNegotiated TmnxBGPFamilyType,
    tBgpPeerOperLLGRStatus           INTEGER,
    tBgpPeerOperLLGRFamilySent       TmnxBGPFamilyType,
    tBgpPeerOperSrplcyV4SupPfxDamp   Counter32,
    tBgpPeerOperSrplcyV4RecvPfxs     Counter32,
    tBgpPeerOperSrplcyV4SentPfxs     Counter32,
    tBgpPeerOperSrplcyV4ActivePfxs   Counter32,
    tBgpPeerOperSrplcyV4RejPfxs      Counter32,
    tBgpPeerRemoteExtNhEncoding      TmnxIpFamily,
    tBgpPeerEORSent                  TmnxIpFamily,
    tBgpPeerEORReceived              TmnxIpFamily,
    tBgpPeerConvExceededMinWait      INTEGER,
    tBgpPeerOperAS4Byte              InetAutonomousSystemNumber,
    tBgpPeerNgOperEPreference        TmnxBgpPreference,
    tBgpPeerNgOperIPreference        TmnxBgpPreference,
    tBgpPeerNgOperELabelPreference   TmnxBgpPreference,
    tBgpPeerNgOperILabelPreference   TmnxBgpPreference,
    tBgpPeerOperSrplcyV6SupPfxDamp   Counter32,
    tBgpPeerOperSrplcyV6RecvPfxs     Counter32,
    tBgpPeerOperSrplcyV6SentPfxs     Counter32,
    tBgpPeerOperSrplcyV6ActivePfxs   Counter32,
    tBgpPeerOperSrplcyV6RejPfxs      Counter32,
    tBgpPeerOperLocalAddressType     InetAddressType,
    tBgpPeerOperLocalAddress         InetAddress,
    tBgpPeerOperRemoteAddressType    InetAddressType,
    tBgpPeerOperRemoteAddress        InetAddress,
    tBgpPeerOperTcpMss               Unsigned32,
    tBgpPeerOperTcpRcvdMss           Unsigned32,
    tBgpPeerNgOperFVIpv4SupPfxDamp   Counter32,
    tBgpPeerNgOperFVIpv4RecvPfxs     Counter32,
    tBgpPeerNgOperFVIpv4SentPfxs     Counter32,
    tBgpPeerNgOperFVIpv4ActivePfxs   Counter32,
    tBgpPeerNgOperFVIpv4RejPfxs      Counter32,
    tBgpPeerNgOperFVIpv6SupPfxDamp   Counter32,
    tBgpPeerNgOperFVIpv6RecvPfxs     Counter32,
    tBgpPeerNgOperFVIpv6SentPfxs     Counter32,
    tBgpPeerNgOperFVIpv6ActivePfxs   Counter32,
    tBgpPeerNgOperFVIpv6RejPfxs      Counter32,
    tBgpPeerFsmEstablishedTime       Gauge32,
    tBgpPeerNgOperLastError          OCTET STRING,
    tBgpPeerNgOperLocalPort          Unsigned32,
    tBgpPeerNgOperRemotePort         Unsigned32,
    tBgpPeerNgOperIdentifier         IpAddress,
    tBgpPeerNgOperInUpdates          Counter32,
    tBgpPeerNgOperOutUpdates         Counter32,
    tBgpPeerNgOperInTotalMessages    Counter32,
    tBgpPeerNgOperOutTotalMessages   Counter32,
    tBgpPeerNgOperInNotifications    Counter32,
    tBgpPeerNgOperOutNotifications   Counter32,
    tBgpPeerNgOperInUpdElapsedTime   Gauge32
}

tBgpPeerNgOperMsgOctetsRcvd      OBJECT-TYPE
    SYNTAX      Counter64
    MAX-ACCESS  read-only
    STATUS      current
    DESCRIPTION
        "The value of tBgpPeerNgOperMsgOctetsRcvd indicates the number of
         octets received from this peer."
    ::= { tBgpPeerNgOperEntry 1 }

tBgpPeerNgOperMsgOctetsSent      OBJECT-TYPE
    SYNTAX      Counter64
    MAX-ACCESS  read-only
    STATUS      current
    DESCRIPTION
        "The value of tBgpPeerNgOperMsgOctetsSent indicates the number of
         octets transmitted to this peer."
    ::= { tBgpPeerNgOperEntry 2 }

tBgpPeerNgOperInputQueueMsgs     OBJECT-TYPE
    SYNTAX      Gauge32
    MAX-ACCESS  read-only
    STATUS      current
    DESCRIPTION
        "The value of tBgpPeerNgOperInputQueueMsgs indicates the number of
         unprocessed messages in the queue, from this peer."
    ::= { tBgpPeerNgOperEntry 3 }

tBgpPeerNgOperOutputQueueMsgs    OBJECT-TYPE
    SYNTAX      Gauge32
    MAX-ACCESS  read-only
    STATUS      current
    DESCRIPTION
        "The value of tBgpPeerNgOperOutputQueueMsgs indicates the number of
         untransmitted messages in the queue, to this peer."
    ::= { tBgpPeerNgOperEntry 4 }

tBgpPeerNgOperReceivedPrefixes   OBJECT-TYPE
    SYNTAX      Counter32
    MAX-ACCESS  read-only
    STATUS      current
    DESCRIPTION
        "The value of tBgpPeerNgOperReceivedPrefixes indicates the number of
         prefixes received from this peer."
    ::= { tBgpPeerNgOperEntry 5 }

tBgpPeerNgOperSentPrefixes       OBJECT-TYPE
    SYNTAX      Counter32
    MAX-ACCESS  read-only
    STATUS      current
    DESCRIPTION
        "The value of tBgpPeerNgOperSentPrefixes indicates the number of
         prefixes transmitted to this peer."
    ::= { tBgpPeerNgOperEntry 6 }

tBgpPeerNgOperActivePrefixes     OBJECT-TYPE
    SYNTAX      Gauge32
    MAX-ACCESS  read-only
    STATUS      current
    DESCRIPTION
        "The value of tBgpPeerNgOperActivePrefixes indicates the number of
         active prefixes from this peer."
    ::= { tBgpPeerNgOperEntry 7 }

tBgpPeerNgOperReceivedPaths      OBJECT-TYPE
    SYNTAX      Counter32
    MAX-ACCESS  read-only
    STATUS      current
    DESCRIPTION
        "The value of tBgpPeerNgOperReceivedPaths indicates the number of paths
         received from this peer."
    ::= { tBgpPeerNgOperEntry 8 }

tBgpPeerNgOperPathsSupByDamping  OBJECT-TYPE
    SYNTAX      Counter32
    MAX-ACCESS  read-only
    STATUS      obsolete
    DESCRIPTION
        "The value of tBgpPeerNgOperPathsSupByDamping indicates the number of
         paths from this peer, which have been suppressed by damping."
    ::= { tBgpPeerNgOperEntry 9 }

tBgpPeerNgOperFlaps              OBJECT-TYPE
    SYNTAX      Counter32
    MAX-ACCESS  read-only
    STATUS      current
    DESCRIPTION
        "The value of tBgpPeerNgOperFlaps indicates the number of flaps of
         updates from this peer."
    ::= { tBgpPeerNgOperEntry 10 }

tBgpPeerNgOperLastState          OBJECT-TYPE
    SYNTAX      BgpPeerState
    MAX-ACCESS  read-only
    STATUS      current
    DESCRIPTION
        "The value of tBgpPeerNgOperLastState indicates the last BGP state of
         this peer."
    ::= { tBgpPeerNgOperEntry 11 }

tBgpPeerNgOperLastEvent          OBJECT-TYPE
    SYNTAX      BgpPeerEvent
    MAX-ACCESS  read-only
    STATUS      current
    DESCRIPTION
        "The value of tBgpPeerNgOperLastEvent indicates the last BGP event of
         this peer."
    ::= { tBgpPeerNgOperEntry 12 }

tBgpPeerNgOperVpnRecvPrefixes    OBJECT-TYPE
    SYNTAX      Counter32
    MAX-ACCESS  read-only
    STATUS      current
    DESCRIPTION
        "The value of tBgpPeerNgOperVpnRecvPrefixes indicates the number of
         received VPN prefixes."
    ::= { tBgpPeerNgOperEntry 13 }

tBgpPeerNgOperVpnSentPrefixes    OBJECT-TYPE
    SYNTAX      Counter32
    MAX-ACCESS  read-only
    STATUS      current
    DESCRIPTION
        "The value of tBgpPeerNgOperVpnSentPrefixes indicates the number of
         transmitted VPN prefixes."
    ::= { tBgpPeerNgOperEntry 14 }

tBgpPeerNgOperVpnActivePrefixes  OBJECT-TYPE
    SYNTAX      Gauge32
    MAX-ACCESS  read-only
    STATUS      current
    DESCRIPTION
        "The value of tBgpPeerNgOperVpnActivePrefixes indicates the number of
         active VPN prefixes from this BGP peer."
    ::= { tBgpPeerNgOperEntry 15 }

tBgpPeerNgOperGRSupport          OBJECT-TYPE
    SYNTAX      TruthValue
    MAX-ACCESS  read-only
    STATUS      current
    DESCRIPTION
        "The value of tBgpPeerNgOperGRSupport indicates whether the BGP peer
         supports graceful restart. If tBgpPeerNgOperGRSupport has a value of
         'true' the peer supports graceful restart."
    ::= { tBgpPeerNgOperEntry 16 }

tBgpPeerNgOperGRFamilyRestart    OBJECT-TYPE
    SYNTAX      TmnxBGPFamilyType
    MAX-ACCESS  read-only
    STATUS      current
    DESCRIPTION
        "The value of tBgpPeerNgOperGRFamilyRestart indicates the capability
         type of NLRI that peer supports restart for."
    ::= { tBgpPeerNgOperEntry 17 }

tBgpPeerNgOperGRFamilyFwding     OBJECT-TYPE
    SYNTAX      TmnxBGPFamilyType
    MAX-ACCESS  read-only
    STATUS      current
    DESCRIPTION
        "The value of tBgpPeerNgOperGRFamilyFwding indicates the capability
         type of NLRI that peer saved forwarding for."
    ::= { tBgpPeerNgOperEntry 18 }

tBgpPeerNgOperGRFamilyNegotiated OBJECT-TYPE
    SYNTAX      TmnxBGPFamilyType
    MAX-ACCESS  read-only
    STATUS      current
    DESCRIPTION
        "The value of tBgpPeerNgOperGRFamilyNegotiated indicates the capability
         type of NLRI that restart is negotiated for by the peer."
    ::= { tBgpPeerNgOperEntry 19 }

tBgpPeerNgOperGRRecvEOR          OBJECT-TYPE
    SYNTAX      TmnxBGPFamilyType
    MAX-ACCESS  read-only
    STATUS      current
    DESCRIPTION
        "The value of tBgpPeerNgOperGRRecvEOR indicates the capability type of
         NLRI of received end-of-rib markers from the peer."
    ::= { tBgpPeerNgOperEntry 20 }

tBgpPeerNgOperGRSendEOR          OBJECT-TYPE
    SYNTAX      TmnxBGPFamilyType
    MAX-ACCESS  read-only
    STATUS      current
    DESCRIPTION
        "The value of tBgpPeerNgOperGRSendEOR indicates the capability type of
         NLRI of all the sent end-of-rib markers by the peer."
    ::= { tBgpPeerNgOperEntry 21 }

tBgpPeerNgOperGRStaleRoutesTime  OBJECT-TYPE
    SYNTAX      Unsigned32
    MAX-ACCESS  read-only
    STATUS      current
    DESCRIPTION
        "The value of tBgpPeerNgOperGRStaleRoutesTime indicates the maximum
         amount of time in seconds that stale routes are maintained by the peer
         after a graceful restart is initiated."
    ::= { tBgpPeerNgOperEntry 22 }

tBgpPeerNgOperGRReqRestartTime   OBJECT-TYPE
    SYNTAX      Unsigned32
    MAX-ACCESS  read-only
    STATUS      current
    DESCRIPTION
        "The value of tBgpPeerNgOperGRReqRestartTime indicates the maximum
         amount of time in seconds that a graceful restart takes for the peer."
    ::= { tBgpPeerNgOperEntry 23 }

tBgpPeerNgOperGRStatus           OBJECT-TYPE
    SYNTAX      INTEGER {
        notHelping       (1),
        restarting       (2),
        restart-complete (3),
        helping          (4)
    }
    MAX-ACCESS  read-only
    STATUS      current
    DESCRIPTION
        "The value of tBgpPeerNgOperGRStatus indicates the graceful restart
         status of the BGP peer.'

         The values of tBgpPeerNgOperGRStatus means:
            notHelping (1),         -- Peer is not currently being helped
            restarting (2),         -- Received restart request from the peer
            restart-complete (3),   -- The peer has completed the most recent
                                       restart
            helping (4)             -- Peer is helping us in restarting."
    ::= { tBgpPeerNgOperEntry 24 }

tBgpPeerNgOperNumRestarts        OBJECT-TYPE
    SYNTAX      Unsigned32
    MAX-ACCESS  read-only
    STATUS      current
    DESCRIPTION
        "The value of tBgpPeerNgOperNumRestarts indicates the number of times
         the peer has attempted restart."
    ::= { tBgpPeerNgOperEntry 25 }

tBgpPeerNgOperLastRestartTime    OBJECT-TYPE
    SYNTAX      TimeStamp
    MAX-ACCESS  read-only
    STATUS      current
    DESCRIPTION
        "The value of tBgpPeerNgOperLastRestartTime indicates the last time the
         peer attempted restart."
    ::= { tBgpPeerNgOperEntry 26 }

tBgpPeerNgOperV6ReceivedPrefixes OBJECT-TYPE
    SYNTAX      Counter32
    MAX-ACCESS  read-only
    STATUS      current
    DESCRIPTION
        "The value of tBgpPeerNgOperV6ReceivedPrefixes indicates the number of
         IPv6 prefixes received from this peer."
    ::= { tBgpPeerNgOperEntry 27 }

tBgpPeerNgOperV6SentPrefixes     OBJECT-TYPE
    SYNTAX      Counter32
    MAX-ACCESS  read-only
    STATUS      current
    DESCRIPTION
        "The value of tBgpPeerNgOperV6SentPrefixes indicates the number of IPv6
         prefixes transmitted to this peer."
    ::= { tBgpPeerNgOperEntry 28 }

tBgpPeerNgOperV6ActivePrefixes   OBJECT-TYPE
    SYNTAX      Gauge32
    MAX-ACCESS  read-only
    STATUS      current
    DESCRIPTION
        "The value of tBgpPeerNgOperV6ActivePrefixes indicates the number of
         active IPv6 prefixes from this peer."
    ::= { tBgpPeerNgOperEntry 29 }

tBgpPeerNgOperV6ReceivedPaths    OBJECT-TYPE
    SYNTAX      Counter32
    MAX-ACCESS  read-only
    STATUS      obsolete
    DESCRIPTION
        "The value of tBgpPeerNgOperV6ReceivedPaths indicates the number of
         IPv6 paths received from this peer."
    ::= { tBgpPeerNgOperEntry 30 }

tBgpPeerNgOperV6SuppPathsDamping OBJECT-TYPE
    SYNTAX      Counter32
    MAX-ACCESS  read-only
    STATUS      obsolete
    DESCRIPTION
        "The value of tBgpPeerNgOperV6SuppPathsDamping indicates the number of
         IPv6 paths from this peer, which have been suppressed by damping."
    ::= { tBgpPeerNgOperEntry 31 }

tBgpPeerNgOperVpnReceivedPaths   OBJECT-TYPE
    SYNTAX      Counter32
    MAX-ACCESS  read-only
    STATUS      obsolete
    DESCRIPTION
        "The value of tBgpPeerNgOperVpnReceivedPaths indicates the number of
         VPN paths received from this peer."
    ::= { tBgpPeerNgOperEntry 32 }

tBgpPeerNgOperV4SuppPfxDamp      OBJECT-TYPE
    SYNTAX      Counter32
    MAX-ACCESS  read-only
    STATUS      current
    DESCRIPTION
        "The value of tBgpPeerNgOperV4SuppPfxDamp indicates the number of IPv6
         prefixes from this peer, which have been suppressed by damping."
    ::= { tBgpPeerNgOperEntry 33 }

tBgpPeerNgOperVpnSuppPfxDamp     OBJECT-TYPE
    SYNTAX      Counter32
    MAX-ACCESS  read-only
    STATUS      current
    DESCRIPTION
        "The value of tBgpPeerNgOperVpnSuppPfxDamp indicates the number of VPN
         IPv4 prefixes from this peer, which have been suppressed by damping."
    ::= { tBgpPeerNgOperEntry 34 }

tBgpPeerNgOperV6SuppPfxDamp      OBJECT-TYPE
    SYNTAX      Counter32
    MAX-ACCESS  read-only
    STATUS      current
    DESCRIPTION
        "The value of tBgpPeerNgOperV6SuppPfxDamp indicates the number of IPv6
         prefixes from this peer, which have been suppressed by damping."
    ::= { tBgpPeerNgOperEntry 35 }

tBgpPeerNgOperMCastV4SuppPfxDamp OBJECT-TYPE
    SYNTAX      Counter32
    MAX-ACCESS  read-only
    STATUS      current
    DESCRIPTION
        "The value of tBgpPeerNgOperMCastV4SuppPfxDamp indicates the number of
         IPv4 multicast prefixes from this peer, which have been suppressed by
         damping."
    ::= { tBgpPeerNgOperEntry 36 }

tBgpPeerNgOperMCastV4RecvPfxs    OBJECT-TYPE
    SYNTAX      Counter32
    MAX-ACCESS  read-only
    STATUS      current
    DESCRIPTION
        "The value of tBgpPeerNgOperMCastV4RecvPfxs indicates the number of
         IPv4 multicast prefixes received from this peer."
    ::= { tBgpPeerNgOperEntry 37 }

tBgpPeerNgOperMCastV4SentPfxs    OBJECT-TYPE
    SYNTAX      Counter32
    MAX-ACCESS  read-only
    STATUS      current
    DESCRIPTION
        "The value of tBgpPeerNgOperMCastV4SentPfxs indicates the number of
         IPv4 multicast prefixes transmitted to this peer."
    ::= { tBgpPeerNgOperEntry 38 }

tBgpPeerNgOperMCastV4ActivePfxs  OBJECT-TYPE
    SYNTAX      Counter32
    MAX-ACCESS  read-only
    STATUS      current
    DESCRIPTION
        "The value of tBgpPeerNgOperMCastV4ActivePfxs indicates the number of
         active IPv4 multicast prefixes from this peer."
    ::= { tBgpPeerNgOperEntry 39 }

tBgpPeerNgOperVpnIpv6RecvPfxs    OBJECT-TYPE
    SYNTAX      Counter32
    MAX-ACCESS  read-only
    STATUS      current
    DESCRIPTION
        "The value of tBgpPeerNgOperVpnIpv6RecvPfxs indicates the number of VPN
         IPv6 prefixes received from this peer."
    ::= { tBgpPeerNgOperEntry 40 }

tBgpPeerNgOperVpnIpv6SentPfxs    OBJECT-TYPE
    SYNTAX      Counter32
    MAX-ACCESS  read-only
    STATUS      current
    DESCRIPTION
        "The value of tBgpPeerNgOperVpnIpv6SentPfxs indicates the number of VPN
         IPv6 prefixes transmitted to this peer."
    ::= { tBgpPeerNgOperEntry 41 }

tBgpPeerNgOperVpnIpv6ActivePfxs  OBJECT-TYPE
    SYNTAX      Gauge32
    MAX-ACCESS  read-only
    STATUS      current
    DESCRIPTION
        "The value of tBgpPeerNgOperVpnIpv6ActivePfxs indicates the number of
         active VPN IPv6 prefixes from this peer."
    ::= { tBgpPeerNgOperEntry 42 }

tBgpPeerNgOperVpnIpv6SuppPfxDamp OBJECT-TYPE
    SYNTAX      Counter32
    MAX-ACCESS  read-only
    STATUS      current
    DESCRIPTION
        "The value of tBgpPeerNgOperVpnIpv6SuppPfxDamp indicates the number of
         VPN IPv6 prefixes from this peer, which have been suppressed by
         damping."
    ::= { tBgpPeerNgOperEntry 43 }

tBgpPeerNgOperMvpnV4SuppPfxDamp  OBJECT-TYPE
    SYNTAX      Counter32
    MAX-ACCESS  read-only
    STATUS      current
    DESCRIPTION
        "The value of tBgpPeerNgOperMvpnV4SuppPfxDamp indicates the number of
         MVPN IPv4 prefixes from this peer, which have been suppressed by
         damping."
    ::= { tBgpPeerNgOperEntry 44 }

tBgpPeerNgOperMvpnV4RecvPfxs     OBJECT-TYPE
    SYNTAX      Counter32
    MAX-ACCESS  read-only
    STATUS      current
    DESCRIPTION
        "The value of tBgpPeerNgOperMvpnV4RecvPfxs indicates the number of MVPN
         IPv4 prefixes received from this peer."
    ::= { tBgpPeerNgOperEntry 45 }

tBgpPeerNgOperMvpnV4SentPfxs     OBJECT-TYPE
    SYNTAX      Counter32
    MAX-ACCESS  read-only
    STATUS      current
    DESCRIPTION
        "The value of tBgpPeerNgOperMvpnV4SentPfxs indicates the number of MVPN
         IPv4 prefixes transmitted to this peer."
    ::= { tBgpPeerNgOperEntry 46 }

tBgpPeerNgOperMvpnV4ActivePfxs   OBJECT-TYPE
    SYNTAX      Counter32
    MAX-ACCESS  read-only
    STATUS      current
    DESCRIPTION
        "The value of tBgpPeerNgOperMvpnV4ActivePfxs indicates the number of
         active MVPN IPv4 prefixes from this peer."
    ::= { tBgpPeerNgOperEntry 47 }

tBgpPeerNgOperl2VpnSuppPfxDamp   OBJECT-TYPE
    SYNTAX      Counter32
    MAX-ACCESS  read-only
    STATUS      current
    DESCRIPTION
        "The value of tBgpPeerNgOperl2VpnSuppPfxDamp indicates the number of
         L2VPN prefixes from this peer, which have been suppressed by damping."
    ::= { tBgpPeerNgOperEntry 48 }

tBgpPeerNgOperl2VpnRecvPfxs      OBJECT-TYPE
    SYNTAX      Counter32
    MAX-ACCESS  read-only
    STATUS      current
    DESCRIPTION
        "The value of tBgpPeerNgOperl2VpnRecvPfxs indicates the number L2VPN
         prefixes received from this peer."
    ::= { tBgpPeerNgOperEntry 49 }

tBgpPeerNgOperl2VpnSentPfxs      OBJECT-TYPE
    SYNTAX      Counter32
    MAX-ACCESS  read-only
    STATUS      current
    DESCRIPTION
        "The value of tBgpPeerNgOperl2VpnSentPfxs indicates the number of L2VPN
         prefixes transmitted to this peer."
    ::= { tBgpPeerNgOperEntry 50 }

tBgpPeerNgOperl2VpnActivePfxs    OBJECT-TYPE
    SYNTAX      Counter32
    MAX-ACCESS  read-only
    STATUS      current
    DESCRIPTION
        "The value of tBgpPeerNgOperl2VpnActivePfxs indicates the number of
         active L2VPN prefixes from this peer."
    ::= { tBgpPeerNgOperEntry 51 }

tBgpPeerNgOperMdtSafiSuppPfxDamp OBJECT-TYPE
    SYNTAX      Counter32
    MAX-ACCESS  read-only
    STATUS      current
    DESCRIPTION
        "The value of tBgpPeerNgOperMdtSafiSuppPfxDamp indicates the number of
         MDT-SAFI prefixes from this peer, which have been suppressed by
         damping."
    ::= { tBgpPeerNgOperEntry 52 }

tBgpPeerNgOperMdtSafiRecvPfxs    OBJECT-TYPE
    SYNTAX      Counter32
    MAX-ACCESS  read-only
    STATUS      current
    DESCRIPTION
        "The value of tBgpPeerNgOperMdtSafiRecvPfxs indicates the number of
         MDT-SAFI prefixes received from this peer."
    ::= { tBgpPeerNgOperEntry 53 }

tBgpPeerNgOperMdtSafiSentPfxs    OBJECT-TYPE
    SYNTAX      Counter32
    MAX-ACCESS  read-only
    STATUS      current
    DESCRIPTION
        "The value of tBgpPeerNgOperMdtSafiSentPfxs indicates the number of
         MDT-SAFI prefixes transmitted to this peer."
    ::= { tBgpPeerNgOperEntry 54 }

tBgpPeerNgOperMdtSafiActivePfxs  OBJECT-TYPE
    SYNTAX      Counter32
    MAX-ACCESS  read-only
    STATUS      current
    DESCRIPTION
        "The value of tBgpPeerNgOperMdtSafiActivePfxs indicates the number of
         active MDT-SAFI prefixes from this peer."
    ::= { tBgpPeerNgOperEntry 55 }

tBgpPeerNgOperMsPwSuppPfxDamp    OBJECT-TYPE
    SYNTAX      Counter32
    MAX-ACCESS  read-only
    STATUS      current
    DESCRIPTION
        "The value of tBgpPeerNgOperMsPwSuppPfxDamp indicates the number of
         MS-PW prefixes from this peer, which have been suppressed by damping."
    ::= { tBgpPeerNgOperEntry 56 }

tBgpPeerNgOperMsPwRecvPfxs       OBJECT-TYPE
    SYNTAX      Counter32
    MAX-ACCESS  read-only
    STATUS      current
    DESCRIPTION
        "The value of tBgpPeerNgOperMsPwRecvPfxs indicates the number of MS-PW
         prefixes received from this peer."
    ::= { tBgpPeerNgOperEntry 57 }

tBgpPeerNgOperMsPwSentPfxs       OBJECT-TYPE
    SYNTAX      Counter32
    MAX-ACCESS  read-only
    STATUS      current
    DESCRIPTION
        "The value of tBgpPeerNgOperMsPwSentPfxs indicates the number of MS-PW
         prefixes transmitted to this peer."
    ::= { tBgpPeerNgOperEntry 58 }

tBgpPeerNgOperMsPwActivePfxs     OBJECT-TYPE
    SYNTAX      Counter32
    MAX-ACCESS  read-only
    STATUS      current
    DESCRIPTION
        "The value of tBgpPeerNgOperMsPwActivePfxs indicates the number of
         active MS-PW prefixes from this peer."
    ::= { tBgpPeerNgOperEntry 59 }

tBgpPeerNgOperFlowIpv4SupPfxDamp OBJECT-TYPE
    SYNTAX      Counter32
    MAX-ACCESS  read-only
    STATUS      current
    DESCRIPTION
        "The value of tBgpPeerNgOperFlowIpv4SupPfxDamp indicates the number of
         flow-ipv4 prefixes from this peer, which have been suppressed by
         damping."
    ::= { tBgpPeerNgOperEntry 60 }

tBgpPeerNgOperFlowIpv4RecvPfxs   OBJECT-TYPE
    SYNTAX      Counter32
    MAX-ACCESS  read-only
    STATUS      current
    DESCRIPTION
        "The value of tBgpPeerNgOperFlowIpv4RecvPfxs indicates the number of
         flow-ipv4 prefixes received from this peer."
    ::= { tBgpPeerNgOperEntry 61 }

tBgpPeerNgOperFlowIpv4SentPfxs   OBJECT-TYPE
    SYNTAX      Counter32
    MAX-ACCESS  read-only
    STATUS      current
    DESCRIPTION
        "The value of tBgpPeerNgOperFlowIpv4SentPfxs indicates the number of
         flow-ipv4 prefixes transmitted to this peer."
    ::= { tBgpPeerNgOperEntry 62 }

tBgpPeerNgOperFlowIpv4ActivePfxs OBJECT-TYPE
    SYNTAX      Counter32
    MAX-ACCESS  read-only
    STATUS      current
    DESCRIPTION
        "The value of tBgpPeerNgOperFlowIpv4ActivePfxs indicates the number of
         active flow-ipv4 prefixes from this peer."
    ::= { tBgpPeerNgOperEntry 63 }

tBgpPeerNgAddPathSendRemoteCaps  OBJECT-TYPE
    SYNTAX      TmnxAddPathAddressFamily
    MAX-ACCESS  read-only
    STATUS      current
    DESCRIPTION
        "The value of tBgpPeerNgAddPathSendRemoteCaps indicates the address
         families for which the add-path send capability is supported on the
         remote end of the BGP Peer."
    ::= { tBgpPeerNgOperEntry 66 }

tBgpPeerNgAddPathRecvRemoteCaps  OBJECT-TYPE
    SYNTAX      TmnxAddPathAddressFamily
    MAX-ACCESS  read-only
    STATUS      current
    DESCRIPTION
        "The value of tBgpPeerNgAddPathRecvRemoteCaps indicates the address
         families for which the add-path receive capability is supported on the
         remote end of the BGP Peer."
    ::= { tBgpPeerNgOperEntry 67 }

tBgpPeerNgOperBackupPrefixes     OBJECT-TYPE
    SYNTAX      Counter32
    MAX-ACCESS  read-only
    STATUS      current
    DESCRIPTION
        "The value of tBgpPeerNgOperBackupPrefixes indicates the number of IPv4
         routes selected as backup from this peer."
    ::= { tBgpPeerNgOperEntry 68 }

tBgpPeerNgOperV6BackupPrefixes   OBJECT-TYPE
    SYNTAX      Counter32
    MAX-ACCESS  read-only
    STATUS      current
    DESCRIPTION
        "The value of tBgpPeerNgOperV6BackupPrefixes indicates the number of
         IPv6 routes selected as backup from this peer."
    ::= { tBgpPeerNgOperEntry 69 }

tBgpPeerNgOperRtTgtSuppPfxDamp   OBJECT-TYPE
    SYNTAX      Counter32
    MAX-ACCESS  read-only
    STATUS      current
    DESCRIPTION
        "The value of tBgpPeerNgOperRtTgtSuppPfxDamp indicates the number of
         route target prefixes from this peer, which have been suppressed by
         damping."
    ::= { tBgpPeerNgOperEntry 70 }

tBgpPeerNgOperRtTgtRecvPfxs      OBJECT-TYPE
    SYNTAX      Counter32
    MAX-ACCESS  read-only
    STATUS      current
    DESCRIPTION
        "The value of tBgpPeerNgOperRtTgtRecvPfxs indicates the number of route
         target prefixes received from this peer."
    ::= { tBgpPeerNgOperEntry 71 }

tBgpPeerNgOperRtTgtSentPfxs      OBJECT-TYPE
    SYNTAX      Counter32
    MAX-ACCESS  read-only
    STATUS      current
    DESCRIPTION
        "The value of tBgpPeerNgOperRtTgtSentPfxs indicates the number of route
         target prefixes transmitted to this peer."
    ::= { tBgpPeerNgOperEntry 72 }

tBgpPeerNgOperRtTgtActivePfxs    OBJECT-TYPE
    SYNTAX      Counter32
    MAX-ACCESS  read-only
    STATUS      current
    DESCRIPTION
        "The value of tBgpPeerNgOperRtTgtActivePfxs indicates the number of
         active route target prefixes from this peer."
    ::= { tBgpPeerNgOperEntry 73 }

tBgpPeerNgOperVpnV4BackupPfxs    OBJECT-TYPE
    SYNTAX      Counter32
    MAX-ACCESS  read-only
    STATUS      current
    DESCRIPTION
        "The value of tBgpPeerNgOperVpnV4BackupPfxs indicates the number of VPN
         IPv4 routes selected as backup from this peer."
    ::= { tBgpPeerNgOperEntry 74 }

tBgpPeerNgOperVpnV6BackupPfxs    OBJECT-TYPE
    SYNTAX      Counter32
    MAX-ACCESS  read-only
    STATUS      current
    DESCRIPTION
        "The value of tBgpPeerNgOperVpnV6BackupPfxs indicates the number of VPN
         IPv6 routes selected as backup from this peer."
    ::= { tBgpPeerNgOperEntry 75 }

tBgpPeerNgOperMcastVpnV4RecvPfxs OBJECT-TYPE
    SYNTAX      Counter32
    MAX-ACCESS  read-only
    STATUS      current
    DESCRIPTION
        "The value of tBgpPeerNgOperMcastVpnV4RecvPfxs indicates the number of
         multicast vpn ipv4 prefixes received from this peer."
    ::= { tBgpPeerNgOperEntry 76 }

tBgpPeerNgOperMcastVpnV4SentPfxs OBJECT-TYPE
    SYNTAX      Counter32
    MAX-ACCESS  read-only
    STATUS      current
    DESCRIPTION
        "The value of tBgpPeerNgOperMcastVpnV4SentPfxs indicates the number of
         multicast vpn ipv4 prefixes transmitted to this peer."
    ::= { tBgpPeerNgOperEntry 77 }

tBgpPeerNgOperMcastVpnV4ActPfxs  OBJECT-TYPE
    SYNTAX      Counter32
    MAX-ACCESS  read-only
    STATUS      current
    DESCRIPTION
        "The value of tBgpPeerNgOperMcastVpnV4ActPfxs indicates the number of
         active multicast vpn ipv4 prefixes from this peer."
    ::= { tBgpPeerNgOperEntry 78 }

tBgpPeerNgOperMvpnV6SuppPfxDamp  OBJECT-TYPE
    SYNTAX      Counter32
    MAX-ACCESS  read-only
    STATUS      current
    DESCRIPTION
        "The value of tBgpPeerNgOperMvpnV6SuppPfxDamp indicates the number of
         MVPN IPv6 prefixes from this peer, which have been suppressed by
         damping."
    ::= { tBgpPeerNgOperEntry 79 }

tBgpPeerNgOperMvpnV6RecvPfxs     OBJECT-TYPE
    SYNTAX      Counter32
    MAX-ACCESS  read-only
    STATUS      current
    DESCRIPTION
        "The value of tBgpPeerNgOperMvpnV6RecvPfxs indicates the number of MVPN
         IPv6 prefixes received from this peer."
    ::= { tBgpPeerNgOperEntry 80 }

tBgpPeerNgOperMvpnV6SentPfxs     OBJECT-TYPE
    SYNTAX      Counter32
    MAX-ACCESS  read-only
    STATUS      current
    DESCRIPTION
        "The value of tBgpPeerNgOperMvpnV6SentPfxs indicates the number of MVPN
         IPv6 prefixes transmitted to this peer."
    ::= { tBgpPeerNgOperEntry 81 }

tBgpPeerNgOperMvpnV6ActivePfxs   OBJECT-TYPE
    SYNTAX      Counter32
    MAX-ACCESS  read-only
    STATUS      current
    DESCRIPTION
        "The value of tBgpPeerNgOperMvpnV6ActivePfxs indicates the number of
         active MVPN IPv6 prefixes from this peer."
    ::= { tBgpPeerNgOperEntry 82 }

tBgpPeerNgOperFlowIpv6SupPfxDamp OBJECT-TYPE
    SYNTAX      Counter32
    MAX-ACCESS  read-only
    STATUS      current
    DESCRIPTION
        "The value of tBgpPeerNgOperFlowIpv6SupPfxDamp indicates the number of
         flow-ipv6 prefixes from this peer, which have been suppressed by
         damping."
    ::= { tBgpPeerNgOperEntry 83 }

tBgpPeerNgOperFlowIpv6RecvPfxs   OBJECT-TYPE
    SYNTAX      Counter32
    MAX-ACCESS  read-only
    STATUS      current
    DESCRIPTION
        "The value of tBgpPeerNgOperFlowIpv6RecvPfxs indicates the number of
         flow-ipv6 prefixes received from this peer."
    ::= { tBgpPeerNgOperEntry 84 }

tBgpPeerNgOperFlowIpv6SentPfxs   OBJECT-TYPE
    SYNTAX      Counter32
    MAX-ACCESS  read-only
    STATUS      current
    DESCRIPTION
        "The value of tBgpPeerNgOperFlowIpv6SentPfxs indicates the number of
         flow-ipv6 prefixes transmitted to this peer."
    ::= { tBgpPeerNgOperEntry 85 }

tBgpPeerNgOperFlowIpv6ActivePfxs OBJECT-TYPE
    SYNTAX      Counter32
    MAX-ACCESS  read-only
    STATUS      current
    DESCRIPTION
        "The value of tBgpPeerNgOperFlowIpv6ActivePfxs indicates the number of
         active flow-ipv6 prefixes from this peer."
    ::= { tBgpPeerNgOperEntry 86 }

tBgpPeerNgOperEvpnSupPfxDamp     OBJECT-TYPE
    SYNTAX      Counter32
    MAX-ACCESS  read-only
    STATUS      current
    DESCRIPTION
        "The value of tBgpPeerNgOperEvpnSupPfxDamp indicates the number of evpn
         prefixes from this peer, which have been suppressed by damping."
    ::= { tBgpPeerNgOperEntry 87 }

tBgpPeerNgOperEvpnRecvPfxs       OBJECT-TYPE
    SYNTAX      Counter32
    MAX-ACCESS  read-only
    STATUS      current
    DESCRIPTION
        "The value of tBgpPeerNgOperEvpnRecvPfxs indicates the number of evpn
         prefixes received from this peer."
    ::= { tBgpPeerNgOperEntry 88 }

tBgpPeerNgOperEvpnSentPfxs       OBJECT-TYPE
    SYNTAX      Counter32
    MAX-ACCESS  read-only
    STATUS      current
    DESCRIPTION
        "The value of tBgpPeerNgOperEvpnSentPfxs indicates the number of evpn
         prefixes transmitted to this peer."
    ::= { tBgpPeerNgOperEntry 89 }

tBgpPeerNgOperEvpnActivePfxs     OBJECT-TYPE
    SYNTAX      Counter32
    MAX-ACCESS  read-only
    STATUS      current
    DESCRIPTION
        "The value of tBgpPeerNgOperEvpnActivePfxs indicates the number of
         active evpn prefixes from this peer."
    ::= { tBgpPeerNgOperEntry 90 }

tBgpPeerNgOperUpdateErrors       OBJECT-TYPE
    SYNTAX      Counter32
    MAX-ACCESS  read-only
    STATUS      current
    DESCRIPTION
        "The value of tBgpPeerNgOperUpdateErrors indicates the number of update
         errors received from this peer."
    ::= { tBgpPeerNgOperEntry 91 }

tBgpPeerNgOperGRNotifFamilyNego  OBJECT-TYPE
    SYNTAX      TmnxBGPFamilyType
    MAX-ACCESS  read-only
    STATUS      current
    DESCRIPTION
        "The value of tBgpPeerNgOperGRNotifFamilyNego indicates the capability
         type of NLRI that NOTIFICATION-triggered restart is negotiated for by
         the peer."
    ::= { tBgpPeerNgOperEntry 92 }

tBgpPeerNgOperRemIdleHoldTime    OBJECT-TYPE
    SYNTAX      Unsigned32
    UNITS       "seconds"
    MAX-ACCESS  read-only
    STATUS      current
    DESCRIPTION
        "The value of tBgpPeerNgOperRemIdleHoldTime indicates how much time is
         remaining until the Idle hold time period runs out and session
         establishment can begin again for this peer."
    ::= { tBgpPeerNgOperEntry 93 }

tBgpPeerNgOperMcastV6SupPfxDamp  OBJECT-TYPE
    SYNTAX      Counter32
    MAX-ACCESS  read-only
    STATUS      current
    DESCRIPTION
        "The value of tBgpPeerNgOperMcastV6SupPfxDamp indicates the number of
         mcast-ipv6 prefixes from this peer, which have been suppressed by
         damping."
    ::= { tBgpPeerNgOperEntry 94 }

tBgpPeerNgOperMcastV6RecvPfxs    OBJECT-TYPE
    SYNTAX      Counter32
    MAX-ACCESS  read-only
    STATUS      current
    DESCRIPTION
        "The value of tBgpPeerNgOperMcastV6RecvPfxs indicates the number of
         mcast-ipv6 prefixes received from this peer."
    ::= { tBgpPeerNgOperEntry 95 }

tBgpPeerNgOperMcastV6SentPfxs    OBJECT-TYPE
    SYNTAX      Counter32
    MAX-ACCESS  read-only
    STATUS      current
    DESCRIPTION
        "The value of tBgpPeerNgOperMcastV6SentPfxs indicates the number of
         mcast-ipv6 prefixes transmitted to this peer."
    ::= { tBgpPeerNgOperEntry 96 }

tBgpPeerNgOperMcastV6ActivePfxs  OBJECT-TYPE
    SYNTAX      Counter32
    MAX-ACCESS  read-only
    STATUS      current
    DESCRIPTION
        "The value of tBgpPeerNgOperMcastV6ActivePfxs indicates the number of
         active mcast-ipv6 prefixes from this peer."
    ::= { tBgpPeerNgOperEntry 97 }

tBgpPeerNgOperIpv4RejPfxs        OBJECT-TYPE
    SYNTAX      Counter32
    MAX-ACCESS  read-only
    STATUS      current
    DESCRIPTION
        "The value of tBgpPeerNgOperIpv4RejPfxs indicates the number of IPv4
         prefixes rejected from this peer."
    ::= { tBgpPeerNgOperEntry 98 }

tBgpPeerNgOperVpnIpv4RejPfxs     OBJECT-TYPE
    SYNTAX      Counter32
    MAX-ACCESS  read-only
    STATUS      current
    DESCRIPTION
        "The value of tBgpPeerNgOperVpnIpv4RejPfxs indicates the number of VPN
         IPv4 prefixes rejected from this peer."
    ::= { tBgpPeerNgOperEntry 99 }

tBgpPeerNgOperIpv6RejPfxs        OBJECT-TYPE
    SYNTAX      Counter32
    MAX-ACCESS  read-only
    STATUS      current
    DESCRIPTION
        "The value of tBgpPeerNgOperIpv6RejPfxs indicates the number of IPv6
         prefixes rejected from this peer."
    ::= { tBgpPeerNgOperEntry 100 }

tBgpPeerNgOperVpnIpv6RejPfxs     OBJECT-TYPE
    SYNTAX      Counter32
    MAX-ACCESS  read-only
    STATUS      current
    DESCRIPTION
        "The value of tBgpPeerNgOperVpnIpv6RejPfxs indicates the number of VPN
         IPv6 prefixes rejected from this peer."
    ::= { tBgpPeerNgOperEntry 101 }

tBgpPeerNgOperMCastV4RejPfxs     OBJECT-TYPE
    SYNTAX      Counter32
    MAX-ACCESS  read-only
    STATUS      current
    DESCRIPTION
        "The value of tBgpPeerNgOperMCastV4RejPfxs indicates the number of IPv4
         multicast prefixes rejected from this peer."
    ::= { tBgpPeerNgOperEntry 102 }

tBgpPeerNgOperl2VpnRejPfxs       OBJECT-TYPE
    SYNTAX      Counter32
    MAX-ACCESS  read-only
    STATUS      current
    DESCRIPTION
        "The value of tBgpPeerNgOperl2VpnRejPfxs indicates the number L2VPN
         prefixes rejected from this peer."
    ::= { tBgpPeerNgOperEntry 103 }

tBgpPeerNgOperMvpnV4RejPfxs      OBJECT-TYPE
    SYNTAX      Counter32
    MAX-ACCESS  read-only
    STATUS      current
    DESCRIPTION
        "The value of tBgpPeerNgOperMvpnV4RejPfxs indicates the number of MVPN
         IPv4 prefixes rejected from this peer."
    ::= { tBgpPeerNgOperEntry 104 }

tBgpPeerNgOperMdtSafiRejPfxs     OBJECT-TYPE
    SYNTAX      Counter32
    MAX-ACCESS  read-only
    STATUS      current
    DESCRIPTION
        "The value of tBgpPeerNgOperMdtSafiRejPfxs indicates the number of
         MDT-SAFI prefixes rejected from this peer."
    ::= { tBgpPeerNgOperEntry 105 }

tBgpPeerNgOperMsPwRejPfxs        OBJECT-TYPE
    SYNTAX      Counter32
    MAX-ACCESS  read-only
    STATUS      current
    DESCRIPTION
        "The value of tBgpPeerNgOperMsPwRejPfxs indicates the number of MS-PW
         prefixes rejected from this peer."
    ::= { tBgpPeerNgOperEntry 106 }

tBgpPeerNgOperFlowIpv4RejPfxs    OBJECT-TYPE
    SYNTAX      Counter32
    MAX-ACCESS  read-only
    STATUS      current
    DESCRIPTION
        "The value of tBgpPeerNgOperFlowIpv4RejPfxs indicates the number of
         flow-ipv4 prefixes rejected from this peer."
    ::= { tBgpPeerNgOperEntry 107 }

tBgpPeerNgOperRtTgtRejPfxs       OBJECT-TYPE
    SYNTAX      Counter32
    MAX-ACCESS  read-only
    STATUS      current
    DESCRIPTION
        "The value of tBgpPeerNgOperRtTgtRejPfxs indicates the number of route
         target prefixes rejected from this peer."
    ::= { tBgpPeerNgOperEntry 108 }

tBgpPeerNgOperMcastVpnV4RejPfxs  OBJECT-TYPE
    SYNTAX      Counter32
    MAX-ACCESS  read-only
    STATUS      current
    DESCRIPTION
        "The value of tBgpPeerNgOperMcastVpnV4RejPfxs indicates the number of
         multicast vpn ipv4 prefixes rejected from this peer."
    ::= { tBgpPeerNgOperEntry 109 }

tBgpPeerNgOperMvpnV6RejPfxs      OBJECT-TYPE
    SYNTAX      Counter32
    MAX-ACCESS  read-only
    STATUS      current
    DESCRIPTION
        "The value of tBgpPeerNgOperMvpnV6RejPfxs indicates the number of MVPN
         IPv6 prefixes rejected from this peer."
    ::= { tBgpPeerNgOperEntry 110 }

tBgpPeerNgOperFlowIpv6RejPfxs    OBJECT-TYPE
    SYNTAX      Counter32
    MAX-ACCESS  read-only
    STATUS      current
    DESCRIPTION
        "The value of tBgpPeerNgOperFlowIpv6RejPfxs indicates the number of
         flow-ipv6 prefixes rejected from this peer."
    ::= { tBgpPeerNgOperEntry 111 }

tBgpPeerNgOperEvpnRejPfxs        OBJECT-TYPE
    SYNTAX      Counter32
    MAX-ACCESS  read-only
    STATUS      current
    DESCRIPTION
        "The value of tBgpPeerNgOperEvpnRejPfxs indicates the number of evpn
         prefixes rejected from this peer."
    ::= { tBgpPeerNgOperEntry 112 }

tBgpPeerNgOperMCastV6RejPfxs     OBJECT-TYPE
    SYNTAX      Counter32
    MAX-ACCESS  read-only
    STATUS      current
    DESCRIPTION
        "The value of tBgpPeerNgOperMCastV6RejPfxs indicates the number of
         mcast-ipv6 prefixes rejected from this peer."
    ::= { tBgpPeerNgOperEntry 113 }

tBgpPeerNgOperMcVpnV4SuppPfxDamp OBJECT-TYPE
    SYNTAX      Counter32
    MAX-ACCESS  read-only
    STATUS      current
    DESCRIPTION
        "The value of tBgpPeerNgOperMcVpnV4SuppPfxDamp indicates the number of
         multicast vpn ipv4 prefixes from this peer, which have been suppressed
         by damping."
    ::= { tBgpPeerNgOperEntry 114 }

tBgpPeerNgOperLabelV4SupPfxDamp  OBJECT-TYPE
    SYNTAX      Counter32
    MAX-ACCESS  read-only
    STATUS      current
    DESCRIPTION
        "The value of tBgpPeerNgOperLabelV4SupPfxDamp indicates the number of
         label-ipv4 prefixes from this peer, which have been suppressed by
         damping."
    ::= { tBgpPeerNgOperEntry 115 }

tBgpPeerNgOperLabelV4RecvPfxs    OBJECT-TYPE
    SYNTAX      Counter32
    MAX-ACCESS  read-only
    STATUS      current
    DESCRIPTION
        "The value of tBgpPeerNgOperLabelV4RecvPfxs indicates the number of
         label-ipv4 prefixes received from this peer."
    ::= { tBgpPeerNgOperEntry 116 }

tBgpPeerNgOperLabelV4SentPfxs    OBJECT-TYPE
    SYNTAX      Counter32
    MAX-ACCESS  read-only
    STATUS      current
    DESCRIPTION
        "The value of tBgpPeerNgOperLabelV4SentPfxs indicates the number of
         label-ipv4 prefixes transmitted to this peer."
    ::= { tBgpPeerNgOperEntry 117 }

tBgpPeerNgOperLabelV4ActivePfxs  OBJECT-TYPE
    SYNTAX      Counter32
    MAX-ACCESS  read-only
    STATUS      current
    DESCRIPTION
        "The value of tBgpPeerNgOperLabelV4ActivePfxs indicates the number of
         active label-ipv4 prefixes from this peer."
    ::= { tBgpPeerNgOperEntry 118 }

tBgpPeerNgOperLabelV4RejPfxs     OBJECT-TYPE
    SYNTAX      Counter32
    MAX-ACCESS  read-only
    STATUS      current
    DESCRIPTION
        "The value of tBgpPeerNgOperLabelV4RejPfxs indicates the number of
         label-ipv4 prefixes rejected from this peer."
    ::= { tBgpPeerNgOperEntry 119 }

tBgpPeerNgOperLabelV4BackupPfxs  OBJECT-TYPE
    SYNTAX      Counter32
    MAX-ACCESS  read-only
    STATUS      current
    DESCRIPTION
        "The value of tBgpPeerNgOperLabelV4BackupPfxs indicates the number of
         label-ipv4 routes selected as backup from this peer."
    ::= { tBgpPeerNgOperEntry 120 }

tBgpPeerNgOperLabelV6SupPfxDamp  OBJECT-TYPE
    SYNTAX      Counter32
    MAX-ACCESS  read-only
    STATUS      current
    DESCRIPTION
        "The value of tBgpPeerNgOperLabelV6SupPfxDamp indicates the number of
         label-ipv6 prefixes from this peer, which have been suppressed by
         damping."
    ::= { tBgpPeerNgOperEntry 121 }

tBgpPeerNgOperLabelV6RecvPfxs    OBJECT-TYPE
    SYNTAX      Counter32
    MAX-ACCESS  read-only
    STATUS      current
    DESCRIPTION
        "The value of tBgpPeerNgOperLabelV6RecvPfxs indicates the number of
         label-ipv6 prefixes received from this peer."
    ::= { tBgpPeerNgOperEntry 122 }

tBgpPeerNgOperLabelV6SentPfxs    OBJECT-TYPE
    SYNTAX      Counter32
    MAX-ACCESS  read-only
    STATUS      current
    DESCRIPTION
        "The value of tBgpPeerNgOperLabelV6SentPfxs indicates the number of
         label-ipv6 prefixes transmitted to this peer."
    ::= { tBgpPeerNgOperEntry 123 }

tBgpPeerNgOperLabelV6ActivePfxs  OBJECT-TYPE
    SYNTAX      Counter32
    MAX-ACCESS  read-only
    STATUS      current
    DESCRIPTION
        "The value of tBgpPeerNgOperLabelV6ActivePfxs indicates the number of
         active label-ipv6 prefixes from this peer."
    ::= { tBgpPeerNgOperEntry 124 }

tBgpPeerNgOperLabelV6RejPfxs     OBJECT-TYPE
    SYNTAX      Counter32
    MAX-ACCESS  read-only
    STATUS      current
    DESCRIPTION
        "The value of tBgpPeerNgOperLabelV6RejPfxs indicates the number of
         label-ipv6 prefixes rejected from this peer."
    ::= { tBgpPeerNgOperEntry 125 }

tBgpPeerNgOperLabelV6BackupPfxs  OBJECT-TYPE
    SYNTAX      Counter32
    MAX-ACCESS  read-only
    STATUS      current
    DESCRIPTION
        "The value of tBgpPeerNgOperLabelV6BackupPfxs indicates the number of
         label-ipv6 routes selected as backup from this peer."
    ::= { tBgpPeerNgOperEntry 126 }

tBgpPeerNgOperBgpLsSupPfxDamp    OBJECT-TYPE
    SYNTAX      Counter32
    MAX-ACCESS  read-only
    STATUS      current
    DESCRIPTION
        "The value of tBgpPeerNgOperBgpLsSupPfxDamp indicates the number of
         bgp-ls prefixes from this peer, which have been suppressed by damping"
    ::= { tBgpPeerNgOperEntry 127 }

tBgpPeerNgOperBgpLsRecvPfxs      OBJECT-TYPE
    SYNTAX      Counter32
    MAX-ACCESS  read-only
    STATUS      current
    DESCRIPTION
        "The value of tBgpPeerNgOperBgpLsRecvPfxs indicates the number of
         bgp-ls prefixes received from this peer."
    ::= { tBgpPeerNgOperEntry 128 }

tBgpPeerNgOperBgpLsSentPfxs      OBJECT-TYPE
    SYNTAX      Counter32
    MAX-ACCESS  read-only
    STATUS      current
    DESCRIPTION
        "The value of tBgpPeerNgOperBgpLsSentPfxs indicates the number of
         bgp-ls prefixes transmitted to this peer."
    ::= { tBgpPeerNgOperEntry 129 }

tBgpPeerNgOperBgpLsActivePfxs    OBJECT-TYPE
    SYNTAX      Counter32
    MAX-ACCESS  read-only
    STATUS      current
    DESCRIPTION
        "The value of tBgpPeerNgOperBgpLsActivePfxs indicates the number of
         active bgp-ls prefixes from this peer."
    ::= { tBgpPeerNgOperEntry 130 }

tBgpPeerNgOperBgpLsRejPfxs       OBJECT-TYPE
    SYNTAX      Counter32
    MAX-ACCESS  read-only
    STATUS      current
    DESCRIPTION
        "The value of tBgpPeerNgOperBgpLsRejPfxs indicates the number of bgp-ls
         prefixes rejected from this peer."
    ::= { tBgpPeerNgOperEntry 131 }

tBgpPeerNgOperMcastVpnV6RecvPfxs OBJECT-TYPE
    SYNTAX      Counter32
    MAX-ACCESS  read-only
    STATUS      current
    DESCRIPTION
        "The value of tBgpPeerNgOperMcastVpnV6RecvPfxs indicates the number of
         multicast vpn ipv6 prefixes received from this peer."
    ::= { tBgpPeerNgOperEntry 132 }

tBgpPeerNgOperMcastVpnV6ActPfxs  OBJECT-TYPE
    SYNTAX      Counter32
    MAX-ACCESS  read-only
    STATUS      current
    DESCRIPTION
        "The value of tBgpPeerNgOperMcastVpnV6ActPfxs indicates the number of
         active multicast vpn ipv6 prefixes from this peer."
    ::= { tBgpPeerNgOperEntry 133 }

tBgpPeerNgOperMcastVpnV6RejPfxs  OBJECT-TYPE
    SYNTAX      Counter32
    MAX-ACCESS  read-only
    STATUS      current
    DESCRIPTION
        "The value of tBgpPeerNgOperMcastVpnV6RejPfxs indicates the number of
         multicast vpn ipv6 prefixes rejected from this peer."
    ::= { tBgpPeerNgOperEntry 134 }

tBgpPeerNgOperMcastVpnV6SentPfxs OBJECT-TYPE
    SYNTAX      Counter32
    MAX-ACCESS  read-only
    STATUS      current
    DESCRIPTION
        "The value of tBgpPeerNgOperMcastVpnV6SentPfxs indicates the number of
         multicast vpn ipv6 prefixes transmitted to this peer."
    ::= { tBgpPeerNgOperEntry 135 }

tBgpPeerNgOperMcVpnV6SuppPfxDamp OBJECT-TYPE
    SYNTAX      Counter32
    MAX-ACCESS  read-only
    STATUS      current
    DESCRIPTION
        "The value of tBgpPeerNgOperMcVpnV6SuppPfxDamp indicates the number of
         multicast vpn ipv6 prefixes from this peer, which have been suppressed
         by damping."
    ::= { tBgpPeerNgOperEntry 136 }

tBgpPeerOperLLGRSupported        OBJECT-TYPE
    SYNTAX      TruthValue
    MAX-ACCESS  read-only
    STATUS      current
    DESCRIPTION
        "The value of tBgpPeerOperLLGRSupported indicates whether the BGP peer
         supports long lived graceful restart. If tBgpPeerOperLLGRSupported has
         a value of 'true' the peer supports long lived graceful restart."
    ::= { tBgpPeerNgOperEntry 137 }

tBgpPeerOperLLGRFamilySupported  OBJECT-TYPE
    SYNTAX      TmnxBGPFamilyType
    MAX-ACCESS  read-only
    STATUS      current
    DESCRIPTION
        "The value of tBgpPeerOperLLGRFamilySupported indicates the capability
         type of NLRI that peer supports Long lived graceful restart for."
    ::= { tBgpPeerNgOperEntry 138 }

tBgpPeerOperLLGRFamilyNegotiated OBJECT-TYPE
    SYNTAX      TmnxBGPFamilyType
    MAX-ACCESS  read-only
    STATUS      current
    DESCRIPTION
        "The value of tBgpPeerOperLLGRFamilyNegotiated indicates the capability
         type of NLRI that long lived GR is negotiated for by the peer."
    ::= { tBgpPeerNgOperEntry 139 }

tBgpPeerOperLLGRStatus           OBJECT-TYPE
    SYNTAX      INTEGER {
        notHelping       (1),
        restarting       (2),
        restart-complete (3),
        helping          (4)
    }
    MAX-ACCESS  read-only
    STATUS      current
    DESCRIPTION
        "The value of tBgpPeerOperLLGRStatus indicates the long lived graceful
         restart status of the BGP peer.'

         The values of tBgpPeerOperLLGRStatus means:
            notHelping (1),         -- Peer is not currently being helped
            restarting (2),         -- Received restart request from the peer
            restart-complete (3),   -- The peer has completed the most recent
                                       restart
            helping (4)             -- Peer is helping us in restarting."
    ::= { tBgpPeerNgOperEntry 140 }

tBgpPeerOperLLGRFamilySent       OBJECT-TYPE
    SYNTAX      TmnxBGPFamilyType
    MAX-ACCESS  read-only
    STATUS      current
    DESCRIPTION
        "The value of tBgpPeerOperLLGRFamilySent indicates the capability type
         of NLRI that long lived GR is configured on this system."
    ::= { tBgpPeerNgOperEntry 141 }

tBgpPeerOperSrplcyV4SupPfxDamp   OBJECT-TYPE
    SYNTAX      Counter32
    MAX-ACCESS  read-only
    STATUS      current
    DESCRIPTION
        "The value of tBgpPeerOperSrplcyV4SupPfxDamp indicates the number of
         srplcy-ipv4 prefixes from this peer, which have been suppressed by
         damping"
    ::= { tBgpPeerNgOperEntry 142 }

tBgpPeerOperSrplcyV4RecvPfxs     OBJECT-TYPE
    SYNTAX      Counter32
    MAX-ACCESS  read-only
    STATUS      current
    DESCRIPTION
        "The value of tBgpPeerOperSrplcyV4RecvPfxs indicates the number of
         srplcy-ipv4 prefixes received from this peer."
    ::= { tBgpPeerNgOperEntry 143 }

tBgpPeerOperSrplcyV4SentPfxs     OBJECT-TYPE
    SYNTAX      Counter32
    MAX-ACCESS  read-only
    STATUS      current
    DESCRIPTION
        "The value of tBgpPeerOperSrplcyV4SentPfxs indicates the number of
         srplcy-ipv4 prefixes transmitted to this peer."
    ::= { tBgpPeerNgOperEntry 144 }

tBgpPeerOperSrplcyV4ActivePfxs   OBJECT-TYPE
    SYNTAX      Counter32
    MAX-ACCESS  read-only
    STATUS      current
    DESCRIPTION
        "The value of tBgpPeerOperSrplcyV4ActivePfxs indicates the number of
         active srplcy-ipv4 prefixes from this peer."
    ::= { tBgpPeerNgOperEntry 145 }

tBgpPeerOperSrplcyV4RejPfxs      OBJECT-TYPE
    SYNTAX      Counter32
    MAX-ACCESS  read-only
    STATUS      current
    DESCRIPTION
        "The value of tBgpPeerOperSrplcyV4RejPfxs indicates the number of
         srplcy-ipv4 prefixes rejected from this peer."
    ::= { tBgpPeerNgOperEntry 146 }

tBgpPeerRemoteExtNhEncoding      OBJECT-TYPE
    SYNTAX      TmnxIpFamily
    MAX-ACCESS  read-only
    STATUS      current
    DESCRIPTION
        "The value of tBgpPeerRemoteExtNhEncoding specifies the types of
         AFI/SAFI the Bgp peer supports for remote extended next-hop encoding."
    ::= { tBgpPeerNgOperEntry 147 }

tBgpPeerEORSent                  OBJECT-TYPE
    SYNTAX      TmnxIpFamily
    MAX-ACCESS  read-only
    STATUS      current
    DESCRIPTION
        "The value of tBgpPeerEORSent specifies the types of AFI/SAFI for which
         the EOR marker was sent."
    ::= { tBgpPeerNgOperEntry 148 }

tBgpPeerEORReceived              OBJECT-TYPE
    SYNTAX      TmnxIpFamily
    MAX-ACCESS  read-only
    STATUS      current
    DESCRIPTION
        "The value of tBgpPeerEORReceived specifies the types of AFI/SAFI for
         which the EOR marker was received."
    ::= { tBgpPeerNgOperEntry 149 }

tBgpPeerConvExceededMinWait      OBJECT-TYPE
    SYNTAX      INTEGER {
        no      (1),
        yes     (2),
        unknown (3)
    }
    MAX-ACCESS  read-only
    STATUS      current
    DESCRIPTION
        "The value of tBgpPeerConvExceededMinWait indicates establishment  of
         session relative to tBgpInstanceConvMinWaitToAdv timer."
    ::= { tBgpPeerNgOperEntry 150 }

tBgpPeerOperAS4Byte              OBJECT-TYPE
    SYNTAX      InetAutonomousSystemNumber
    MAX-ACCESS  read-only
    STATUS      current
    DESCRIPTION
        "The value of tBgpPeerOperAS4Byte indicates the autonomous system
         number for the dynamic neighbor."
    ::= { tBgpPeerNgOperEntry 151 }

tBgpPeerNgOperEPreference        OBJECT-TYPE
    SYNTAX      TmnxBgpPreference (0..255)
    MAX-ACCESS  read-only
    STATUS      current
    DESCRIPTION
        "The value of tBgpPeerNgOperEPreference specifies the route preference
         for ebgp routes."
    DEFVAL      { 0 }
    ::= { tBgpPeerNgOperEntry 152 }

tBgpPeerNgOperIPreference        OBJECT-TYPE
    SYNTAX      TmnxBgpPreference (0..255)
    MAX-ACCESS  read-only
    STATUS      current
    DESCRIPTION
        "The value of tBgpPeerNgOperIPreference specifies the route preference
         for ibgp routes."
    DEFVAL      { 0 }
    ::= { tBgpPeerNgOperEntry 153 }

tBgpPeerNgOperELabelPreference   OBJECT-TYPE
    SYNTAX      TmnxBgpPreference (0..255)
    MAX-ACCESS  read-only
    STATUS      current
    DESCRIPTION
        "The value of tBgpPeerNgOperELabelPreference specifies the route
         preference for label-IPv4 and label-IPv6 ebgp routes."
    DEFVAL      { 0 }
    ::= { tBgpPeerNgOperEntry 154 }

tBgpPeerNgOperILabelPreference   OBJECT-TYPE
    SYNTAX      TmnxBgpPreference (0..255)
    MAX-ACCESS  read-only
    STATUS      current
    DESCRIPTION
        "The value of tBgpPeerNgOperILabelPreference specifies the route
         preference for label-IPv4 and label-IPv6 ibgp routes."
    DEFVAL      { 0 }
    ::= { tBgpPeerNgOperEntry 155 }

tBgpPeerOperSrplcyV6SupPfxDamp   OBJECT-TYPE
    SYNTAX      Counter32
    MAX-ACCESS  read-only
    STATUS      current
    DESCRIPTION
        "The value of tBgpPeerOperSrplcyV6SupPfxDamp indicates the number of
         srplcy-ipv6 prefixes from this peer, which have been suppressed by
         damping"
    ::= { tBgpPeerNgOperEntry 156 }

tBgpPeerOperSrplcyV6RecvPfxs     OBJECT-TYPE
    SYNTAX      Counter32
    MAX-ACCESS  read-only
    STATUS      current
    DESCRIPTION
        "The value of tBgpPeerOperSrplcyV6RecvPfxs indicates the number of
         srplcy-ipv6 prefixes received from this peer."
    ::= { tBgpPeerNgOperEntry 157 }

tBgpPeerOperSrplcyV6SentPfxs     OBJECT-TYPE
    SYNTAX      Counter32
    MAX-ACCESS  read-only
    STATUS      current
    DESCRIPTION
        "The value of tBgpPeerOperSrplcyV6SentPfxs indicates the number of
         srplcy-ipv6 prefixes transmitted to this peer."
    ::= { tBgpPeerNgOperEntry 158 }

tBgpPeerOperSrplcyV6ActivePfxs   OBJECT-TYPE
    SYNTAX      Counter32
    MAX-ACCESS  read-only
    STATUS      current
    DESCRIPTION
        "The value of tBgpPeerOperSrplcyV6ActivePfxs indicates the number of
         active srplcy-ipv6 prefixes from this peer."
    ::= { tBgpPeerNgOperEntry 159 }

tBgpPeerOperSrplcyV6RejPfxs      OBJECT-TYPE
    SYNTAX      Counter32
    MAX-ACCESS  read-only
    STATUS      current
    DESCRIPTION
        "The value of tBgpPeerOperSrplcyV6RejPfxs indicates the number of
         srplcy-ipv6 prefixes rejected from this peer."
    ::= { tBgpPeerNgOperEntry 160 }

tBgpPeerOperLocalAddressType     OBJECT-TYPE
    SYNTAX      InetAddressType
    MAX-ACCESS  read-only
    STATUS      current
    DESCRIPTION
        "The value of tBgpPeerOperLocalAddressType specifies the address type
         of the local address. tBgpPeerOperLocalAddressType can be either
         unknown, ipv4 or ipv6."
    ::= { tBgpPeerNgOperEntry 161 }

tBgpPeerOperLocalAddress         OBJECT-TYPE
    SYNTAX      InetAddress (SIZE (0|4|16))
    MAX-ACCESS  read-only
    STATUS      current
    DESCRIPTION
        "The value of tBgpPeerOperLocalAddress specifies the local address.

         If the tBgpPeerOperLocalAddressType is set to ipv4, then the local
         address is an ipv4 address, if the tBgpPeerOperLocalAddressType is set
         to ipv6, the local address is an ipv6 address.

         If local address is not set, tBgpPeerOperLocalAddressType is set to
         unknown and tBgpPeerOperLocalAddress returns a null string."
    ::= { tBgpPeerNgOperEntry 162 }

tBgpPeerOperRemoteAddressType    OBJECT-TYPE
    SYNTAX      InetAddressType
    MAX-ACCESS  read-only
    STATUS      current
    DESCRIPTION
        "The value of tBgpPeerOperRemoteAddressType specifies the address type
         of the remote address. tBgpPeerOperRemoteAddressType can be either
         unknown, ipv4 or ipv6."
    ::= { tBgpPeerNgOperEntry 163 }

tBgpPeerOperRemoteAddress        OBJECT-TYPE
    SYNTAX      InetAddress (SIZE (0|4|16))
    MAX-ACCESS  read-only
    STATUS      current
    DESCRIPTION
        "The value of tBgpPeerOperRemoteAddress specifies the remote address.

         If the tBgpPeerOperRemoteAddressType is set to ipv4, then the remote
         address is an ipv4 address, if the tBgpPeerOperRemoteAddressType is
         set to ipv6, the remote address is an ipv6 address.

         If remote address is not set, tBgpPeerOperRemoteAddressType is set to
         unknown and tBgpPeerOperRemoteAddress returns a null string."
    ::= { tBgpPeerNgOperEntry 164 }

tBgpPeerOperTcpMss               OBJECT-TYPE
    SYNTAX      Unsigned32
    MAX-ACCESS  read-only
    STATUS      current
    DESCRIPTION
        "The value of tBgpPeerOperTcpMss specifies the current maximum size of
         TCP segments that can be sent to the peer."
    ::= { tBgpPeerNgOperEntry 165 }

tBgpPeerOperTcpRcvdMss           OBJECT-TYPE
    SYNTAX      Unsigned32
    MAX-ACCESS  read-only
    STATUS      current
    DESCRIPTION
        "tBgpPeerOperTcpRcvdMss specifies the value of the TCP MSS option
         received from the remote peer."
    ::= { tBgpPeerNgOperEntry 166 }

tBgpPeerNgOperFVIpv4SupPfxDamp   OBJECT-TYPE
    SYNTAX      Counter32
    MAX-ACCESS  read-only
    STATUS      current
    DESCRIPTION
        "The value of tBgpPeerNgOperFVIpv4SupPfxDamp indicates the number of
         flow-vpn-ipv4 prefixes from this peer, which have been suppressed by
         damping."
    ::= { tBgpPeerNgOperEntry 167 }

tBgpPeerNgOperFVIpv4RecvPfxs     OBJECT-TYPE
    SYNTAX      Counter32
    MAX-ACCESS  read-only
    STATUS      current
    DESCRIPTION
        "The value of tBgpPeerNgOperFVIpv4RecvPfxs indicates the number of
         flow-vpn-ipv4 prefixes received from this peer."
    ::= { tBgpPeerNgOperEntry 168 }

tBgpPeerNgOperFVIpv4SentPfxs     OBJECT-TYPE
    SYNTAX      Counter32
    MAX-ACCESS  read-only
    STATUS      current
    DESCRIPTION
        "The value of tBgpPeerNgOperFVIpv4SentPfxs indicates the number of
         flow-vpn-ipv4 prefixes transmitted to this peer."
    ::= { tBgpPeerNgOperEntry 169 }

tBgpPeerNgOperFVIpv4ActivePfxs   OBJECT-TYPE
    SYNTAX      Counter32
    MAX-ACCESS  read-only
    STATUS      current
    DESCRIPTION
        "The value of tBgpPeerNgOperFVIpv4ActivePfxs indicates the number of
         active flow-vpn-ipv4 prefixes from this peer."
    ::= { tBgpPeerNgOperEntry 170 }

tBgpPeerNgOperFVIpv4RejPfxs      OBJECT-TYPE
    SYNTAX      Counter32
    MAX-ACCESS  read-only
    STATUS      current
    DESCRIPTION
        "The value of tBgpPeerNgOperFVIpv4RejPfxs indicates the number of
         flow-vpn-ipv4 prefixes rejected from this peer."
    ::= { tBgpPeerNgOperEntry 171 }

tBgpPeerNgOperFVIpv6SupPfxDamp   OBJECT-TYPE
    SYNTAX      Counter32
    MAX-ACCESS  read-only
    STATUS      current
    DESCRIPTION
        "The value of tBgpPeerNgOperFVIpv6SupPfxDamp indicates the number of
         flow-vpn-ipv6 prefixes from this peer, which have been suppressed by
         damping."
    ::= { tBgpPeerNgOperEntry 172 }

tBgpPeerNgOperFVIpv6RecvPfxs     OBJECT-TYPE
    SYNTAX      Counter32
    MAX-ACCESS  read-only
    STATUS      current
    DESCRIPTION
        "The value of tBgpPeerNgOperFVIpv6RecvPfxs indicates the number of
         flow-vpn-ipv6 prefixes received from this peer."
    ::= { tBgpPeerNgOperEntry 173 }

tBgpPeerNgOperFVIpv6SentPfxs     OBJECT-TYPE
    SYNTAX      Counter32
    MAX-ACCESS  read-only
    STATUS      current
    DESCRIPTION
        "The value of tBgpPeerNgOperFVIpv6SentPfxs indicates the number of
         flow-vpn-ipv6 prefixes transmitted to this peer."
    ::= { tBgpPeerNgOperEntry 174 }

tBgpPeerNgOperFVIpv6ActivePfxs   OBJECT-TYPE
    SYNTAX      Counter32
    MAX-ACCESS  read-only
    STATUS      current
    DESCRIPTION
        "The value of tBgpPeerNgOperFVIpv6ActivePfxs indicates the number of
         active flow-vpn-ipv6 prefixes from this peer."
    ::= { tBgpPeerNgOperEntry 175 }

tBgpPeerNgOperFVIpv6RejPfxs      OBJECT-TYPE
    SYNTAX      Counter32
    MAX-ACCESS  read-only
    STATUS      current
    DESCRIPTION
        "The value of tBgpPeerNgOperFVIpv6RejPfxs indicates the number of
         flow-vpn-ipv6 prefixes rejected from this peer."
    ::= { tBgpPeerNgOperEntry 176 }

tBgpPeerFsmEstablishedTime       OBJECT-TYPE
    SYNTAX      Gauge32
    UNITS       "seconds"
    MAX-ACCESS  read-only
    STATUS      current
    DESCRIPTION
        "This timer indicates how long (in
         seconds) this peer has been in the
         established state or how long
         since this peer was last in the
         established state.  It is set to zero when
         a new peer is configured or when the router is
         booted."
    REFERENCE
        "BGP4-MIB.bgpPeerConnectRetryInterval"
    ::= { tBgpPeerNgOperEntry 177 }

tBgpPeerNgOperLastError          OBJECT-TYPE
    SYNTAX      OCTET STRING (SIZE (2))
    MAX-ACCESS  read-only
    STATUS      current
    DESCRIPTION
        "The value of tBgpPeerNgOperLastError indicates the last error code and
         subcode seen by this peer on this connection. If no error has
         occurred, two zero octets are returned. Otherwise, the first octet of
         this two-byte OCTET STRING contains the error code, and the second
         octet contains the subcode."
    REFERENCE
        "BGP4-MIB.bgpPeerLastError"
    ::= { tBgpPeerNgOperEntry 178 }

tBgpPeerNgOperLocalPort          OBJECT-TYPE
    SYNTAX      Unsigned32 (0..65535)
    MAX-ACCESS  read-only
    STATUS      current
    DESCRIPTION
        "The value of tBgpPeerNgOperLocalPort specifies the local port for the
         TCP connection between the BGP peers.  This value is 0 unless the
         tBgpPeerNgOperStatus is in the openconfirm (5) or the established (6) state."
    REFERENCE
        "BGP4-MIB.bgpPeerLocalPort"
    ::= { tBgpPeerNgOperEntry 179 }

tBgpPeerNgOperRemotePort         OBJECT-TYPE
    SYNTAX      Unsigned32 (0..65535)
    MAX-ACCESS  read-only
    STATUS      current
    DESCRIPTION
        "The value of tBgpPeerNgOperRemotePort specifies the remote port for the
         TCP connection between the BGP peers.  This value is 0 unless the
         tBgpPeerNgOperStatus is in the openconfirm (5) or the established (6) state."
    REFERENCE
        "BGP4-MIB.bgpPeerRemotePort"
    ::= { tBgpPeerNgOperEntry 180 }

tBgpPeerNgOperIdentifier         OBJECT-TYPE
    SYNTAX      IpAddress
    MAX-ACCESS  read-only
    STATUS      current
    DESCRIPTION
        "The value of tBgpPeerNgOperIdentifier specifies the BGP Identifier of this entry's
         BGP peer.  This value is 0.0.0.0 unless the tBgpPeerNgOperStatus is in the openconfirm (5)
         or the established (6) state."
    REFERENCE
        "BGP4-MIB.bgpPeerIdentifier"
    ::= { tBgpPeerNgOperEntry 181 }

tBgpPeerNgOperInUpdates          OBJECT-TYPE
    SYNTAX      Counter32
    MAX-ACCESS  read-only
    STATUS      current
    DESCRIPTION
        "The value of tBgpPeerNgOperInUpdates indicates the number of BGP
         UPDATE messages received from the remote peer."
    REFERENCE
        "BGP4-MIB.bgpPeerInUpdates"
    ::= { tBgpPeerNgOperEntry 182 }

tBgpPeerNgOperOutUpdates         OBJECT-TYPE
    SYNTAX      Counter32
    MAX-ACCESS  read-only
    STATUS      current
    DESCRIPTION
        "The value of tBgpPeerNgOperOutUpdates indicates the number of BGP
         UPDATE messages transmitted to the remote peer."
    REFERENCE
        "BGP4-MIB.bgpPeerOutUpdates"
    ::= { tBgpPeerNgOperEntry 183 }

tBgpPeerNgOperInTotalMessages    OBJECT-TYPE
    SYNTAX      Counter32
    MAX-ACCESS  read-only
    STATUS      current
    DESCRIPTION
        "The value of tBgpPeerNgOperInTotalMessages indicates the total number
         of BGP messages received from the remote peer.."
    REFERENCE
        "BGP4-MIB.bgpPeerInTotalMessages"
    ::= { tBgpPeerNgOperEntry 184 }

tBgpPeerNgOperOutTotalMessages   OBJECT-TYPE
    SYNTAX      Counter32
    MAX-ACCESS  read-only
    STATUS      current
    DESCRIPTION
        "The value of tBgpPeerNgOperOutTotalMessages indicates the total number
         of BGP messages transmitted to the remote peer.."
    REFERENCE
        "BGP4-MIB.bgpPeerOutTotalMessages"
    ::= { tBgpPeerNgOperEntry 185 }

tBgpPeerNgOperInNotifications    OBJECT-TYPE
    SYNTAX      Counter32
    MAX-ACCESS  read-only
    STATUS      current
    DESCRIPTION
        "The value of tBgpPeerNgOperInNotifications indicates the number of BGP
         NOTIFICATION messages received from the remote peer.."
    ::= { tBgpPeerNgOperEntry 186 }

tBgpPeerNgOperOutNotifications   OBJECT-TYPE
    SYNTAX      Counter32
    MAX-ACCESS  read-only
    STATUS      current
    DESCRIPTION
        "The value of tBgpPeerNgOperOutNotifications indicates the number of
         BGP NOTIFICATION messages transmitted to the remote peer.."
    ::= { tBgpPeerNgOperEntry 187 }

tBgpPeerNgOperInUpdElapsedTime   OBJECT-TYPE
    SYNTAX      Gauge32
    MAX-ACCESS  read-only
    STATUS      current
    DESCRIPTION
        "The value of tBgpPeerNgOperInUpdElapsedTime indicates the elapsed time (in seconds) since the last
         BGP UPDATE message was received from the peer.  Each time bgpPeerInUpdates is incremented,
         the value of this object is set to zero (0)."
    REFERENCE
        "BGP4-MIB.bgpPeerInUpdateElapsedTime"
    ::= { tBgpPeerNgOperEntry 188 }

tBgpPeerNgSendOrfRouteTargetTable OBJECT-TYPE
    SYNTAX      SEQUENCE OF TBgpPeerNgSendOrfRouteTargetEntry
    MAX-ACCESS  not-accessible
    STATUS      current
    DESCRIPTION
        "The tBgpPeerNgSendOrfRouteTargetTable provides information about the
         route targets to be advertised to the peers if it is Outbound route
         filtering capable."
    ::= { tBgpPeerObjects 9 }

tBgpPeerNgSendOrfRouteTargetEntry OBJECT-TYPE
    SYNTAX      TBgpPeerNgSendOrfRouteTargetEntry
    MAX-ACCESS  not-accessible
    STATUS      current
    DESCRIPTION
        "Defines an entry in the tBgpPeerNgSendOrfRouteTargetTable. Each entry
         represents a route target to be advertised to the peer."
    INDEX       {
        tBgpPeerNgInstanceIndex,
        tBgpPeerNgAddressType,
        tBgpPeerNgAddress,
        IMPLIED tBgpPeerNgSendOrfRouteTarget
    }
    ::= { tBgpPeerNgSendOrfRouteTargetTable 1 }

TBgpPeerNgSendOrfRouteTargetEntry ::= SEQUENCE
{
    tBgpPeerNgSendOrfRouteTarget     TNamedItem,
    tBgpPeerNgSendOrfRTRowStatus     RowStatus
}

tBgpPeerNgSendOrfRouteTarget     OBJECT-TYPE
    SYNTAX      TNamedItem
    MAX-ACCESS  not-accessible
    STATUS      current
    DESCRIPTION
        "Index for the tBgpPeerNgSendOrfRouteTargetTable. The value of
         tBgpPeerNgSendOrfRouteTarget specifies the extended community name to
         be advertised to the peer."
    ::= { tBgpPeerNgSendOrfRouteTargetEntry 1 }

tBgpPeerNgSendOrfRTRowStatus     OBJECT-TYPE
    SYNTAX      RowStatus
    MAX-ACCESS  read-create
    STATUS      current
    DESCRIPTION
        "The value of tBgpPeerNgSendOrfRTRowStatus controls creation and
         deletion of row entries in the tBgpPeerNgSendOrfRouteTargetTable."
    ::= { tBgpPeerNgSendOrfRouteTargetEntry 2 }

tBgpPeerNgParamsTable            OBJECT-TYPE
    SYNTAX      SEQUENCE OF TBgpPeerNgParamsEntry
    MAX-ACCESS  not-accessible
    STATUS      current
    DESCRIPTION
        "tBgpPeerNgParamsTable provides information about the attributes
         configured for the BGP instance."
    ::= { tBgpPeerObjects 10 }

tBgpPeerNgParamsEntry            OBJECT-TYPE
    SYNTAX      TBgpPeerNgParamsEntry
    MAX-ACCESS  not-accessible
    STATUS      current
    DESCRIPTION
        "An entry in the tBgpPeerNgParamsTable. Each entry maintains the
         attributes configured for BGP instance."
    AUGMENTS    { tBgpPeerNgEntry }
    ::= { tBgpPeerNgParamsTable 1 }

TBgpPeerNgParamsEntry            ::= SEQUENCE
{
    tBgpPeerNgParamsInheritance      Counter64,
    tBgpPeerNgDisableFEFailover      TruthValue,
    tBgpPeerNgDisableComms           TruthValue,
    tBgpPeerNgDisableExtComms        TruthValue,
    tBgpPeerNgDefaultOriginate       TmnxIpFamily,
    tBgpPeerNgAdvertiseInactiveRts   TruthValue,
    tBgpPeerNgMinTTLValue            Unsigned32,
    tBgpPeerNgTracking               TruthValue,
    tBgpPeerNgAdvLabelAddrFamily     TmnxAdvLabelAddressFamily,
    tBgpPeerNgAuthKeyChain           TNamedItemOrEmpty,
    tBgpPeerNgLastError              OCTET STRING,
    tBgpPeerNgBfdEnabled             TruthValue,
    tBgpPeerNgPMTUDiscovery          TruthValue,
    tBgpPeerNgAdvertiseLdpPrefix     TruthValue,
    tBgpPeerNgEnableAddPath          TruthValue,
    tBgpPeerNgRecvAddPath            TmnxAddPathAddressFamily,
    tBgpPeerNgIpv4AddPathLimit       TmnxAddPathSendLimit,
    tBgpPeerNgVpnIpv4AddPathLimit    TmnxAddPathSendLimit,
    tBgpPeerNgIpv6AddPathLimit       TmnxAddPathSendLimit,
    tBgpPeerNgVpnIpv6AddPathLimit    TmnxAddPathSendLimit,
    tBgpPeerNgFlowspecValidate       TruthValue,
    tBgpPeerNgUpdatedErrorHandling   TruthValue,
    tBgpPeerNgDefaultRouteTarget     TruthValue,
    tBgpPeerNgAigp                   TruthValue,
    tBgpPeerNgMinHoldTime            BgpHoldTime,
    tBgpPeerNgSplitHorizon           TruthValue,
    tBgpPeerNgRemPrivateSkipPeerAs   TruthValue,
    tBgpPeerNgLclASNoPrependGlobalAS TruthValue,
    tBgpPeerNgMaxPrefixIdleTimeOut   Integer32,
    tBgpPeerNgGRRestartNotification  TruthValue,
    tBgpPeerNgFaultTolerance         TruthValue,
    tBgpPeerNgDampPeerOscillations   TruthValue,
    tBgpPeerNgDampOscInitialWaitTime Unsigned32,
    tBgpPeerNgDampOscSecondWaitTime  Unsigned32,
    tBgpPeerNgDampOscMaxWaitTime     Unsigned32,
    tBgpPeerNgDampOscErrorInterval   Unsigned32,
    tBgpPeerNgNhUnchangedFamily      TmnxIpNhChgFamily,
    tBgpPeerNgEnableOriginValidation TmnxIpFamily,
    tBgpPeerNgThirdPartyNextHop      TruthValue,
    tBgpPeerNgAddLinkBandwidth       TmnxIpFamily,
    tBgpPeerNgDefRxEvpnEncap         INTEGER,
    tBgpPeerNgLabelResolveStatic     TruthValue,
    tBgpPeerNgLblIpv4AddPathLimit    TmnxAddPathSendLimit,
    tBgpPeerNgLblIpv6AddPathLimit    TmnxAddPathSendLimit,
    tBgpPeerNgLabelPreference        TmnxBgpPreference,
    tBgpPeerNgORRLocation            Unsigned32,
    tBgpPeerNgORRAllowLocalFallbk    TruthValue,
    tBgpPeerNgEnforceFirstAS         TruthValue,
    tBgpPeerNgMvpnIpv4AddPathLimit   Integer32,
    tBgpPeerNgMvpnIpv6AddPathLimit   Integer32,
    tBgpPeerNgMcastVpnV4AddPathLimit Integer32,
    tBgpPeerNgMcastVpnV6AddPathLimit Integer32,
    tBgpPeerLLGRAdvStaleTime         Unsigned32,
    tBgpPeerLLGROvrideStaleTime      Unsigned32,
    tBgpPeerLLGROvrideResTime        Unsigned32,
    tBgpPeerLLGRFwdingBitsSet        INTEGER,
    tBgpPeerLLGRAdvStaleToNeigh      TruthValue,
    tBgpPeerLLGRAdvToNeighWthoutNoEx TruthValue,
    tBgpPeerLLGR                     TruthValue,
    tBgpPeerLocalAddressIfName       TNamedItemOrEmpty,
    tBgpPeerAdvIpv6NhFamily          TmnxIpFamily,
    tBgpPeerExtendNhEncoding         TmnxIpFamily,
    tBgpPeerBypassMRAITimer          TruthValue,
    tBgpPeerNgEvpnAddPathLimit       TmnxAddPathSendLimit
}

tBgpPeerNgParamsInheritance      OBJECT-TYPE
    SYNTAX      Counter64
    MAX-ACCESS  read-create
    STATUS      current
    DESCRIPTION
        "The value of tBgpPeerNgParamsInheritance specifies if the peer entry
         in this row, should inherit the operational value of an object, or use
         the administratively set value.

         This object is a bit-mask, with the following positions:

         tBgpPeerNgDisableFEFailover        0x0000000000000002
         tBgpPeerNgDisableComms             0x0000000000000004
         tBgpPeerNgDisableExtComms          0x0000000000000008
         tBgpPeerNgDefaultOriginate         0x0000000000000010
         tBgpPeerNgAdvertiseInactiveRts     0x0000000000000020
         tBgpPeerNgMinTTLValue              0x0000000000000040
         tBgpPeerNgTracking                 0x0000000000000080
         tBgpPeerNgAdvLabelAddrFamily       0x0000000000000200
         tBgpPeerNgAuthKeyChain             0x0000000000000400
         tBgpPeerNgBfdEnabled               0x0000000000000800
         tBgpPeerNgPMTUDiscovery            0x0000000000002000
         tBgpPeerNgAdvertiseLdpPrefix       0x0000000000004000
         tBgpPeerNgEnableAddPath            0x0000000000010000 #obsoleted 22.2
         tBgpPeerNgRecvAddPath              0x0000000000020000 #obsoleted 22.2
         tBgpPeerNgIpv4AddPathLimit         0x0000000000040000 #obsoleted 22.2
         tBgpPeerNgVpnIpv4AddPathLimit      0x0000000000080000 #obsoleted 22.2
         tBgpPeerNgIpv6AddPathLimit         0x0000000000100000 #obsoleted 22.2
         tBgpPeerNgVpnIpv6AddPathLimit      0x0000000000200000 #obsoleted 22.2
         tBgpPeerNgFlowspecValidate         0x0000000000400000
         tBgpPeerNgUpdatedErrorHandling     0x0000000000800000
         tBgpPeerNgDefaultRouteTarget       0x0000000001000000
         tBgpPeerNgAigp                     0x0000000002000000
         tBgpPeerNgRemPrivateSkipPeerAs     0x0000000010000000
         tBgpPeerNgLclASNoPrependGlobalAS   0x0000000020000000
         tBgpPeerNgGRRestartNotification    0x0000000080000000
         tBgpPeerNgFaultTolerance           0x0000000000008000
         tBgpPeerNgDampPeerOscillations     0x0000000100000000
         tBgpPeerNgSplitHorizon             0x0000000008000000
         tBgpPeerNgNhUnchangedFamily        0x0000002000000000
         tBgpPeerNgEnableOriginValidation   0x0000004000000000
         tBgpPeerNgThirdPartyNextHop        0x0000008000000000
         tBgpPeerNgAddLinkBandwidth         0x0000010000000000
         tBgpPeerNgDefRxEvpnEncap           0x0000020000000000
         tBgpPeerNgLblIpv4AddPathLimit      0x0000080000000000 #obsoleted 22.2
         tBgpPeerNgLblIpv6AddPathLimit      0x0000100000000000 #obsoleted 22.2
         tBgpPeerNgLabelPreference          0x0000200000000000
         tBgpPeerNgEnforceFirstAS           0x0001000000000000
         tBgpPeerNgMvpnIpv4AddPathLimit     0x0002000000000000 #obsoleted 22.2
         tBgpPeerNgMvpnIpv6AddPathLimit     0x0004000000000000 #obsoleted 22.2
         tBgpPeerNgMcastVpnV4AddPathLimit   0x0008000000000000 #obsoleted 22.2
         tBgpPeerNgMcastVpnV6AddPathLimit   0x0010000000000000 #obsoleted 22.2
         tBgpPeerLLGR                       0x0800000000000000
         tBgpPeerLocalAddressIfName         0x1000000000000000
         tBgpPeerAdvIpv6NhFamily            0x2000000000000000
         tBgpPeerExtendNhEncoding           0x4000000000000000
         tBgpPeerBypassMRAITimer            0x8000000000000000
         tBgpPeerNgEvpnAddPathLimit         0x0000040000000000 #obsoleted 22.2

         When the bit for an object is set to one, then the object's
         administrative and operational value are whatever the DEFVAL or most
         recently SET value is.

         When the bit for an object is set to zero, then the object's
         administrative and operational value are inherited from the
         corresponding object in tBgpPeerGroupTable, or from the corresponding
         object in tBgpInstanceTable.

         By default all of these attributes should be inherited from the
         tBgpPeerGroupTable."
    DEFVAL      { 0 }
    ::= { tBgpPeerNgParamsEntry 1 }

tBgpPeerNgDisableFEFailover      OBJECT-TYPE
    SYNTAX      TruthValue
    MAX-ACCESS  read-create
    STATUS      current
    DESCRIPTION
        "The value of tBgpPeerNgDisableFEFailover specifies whether the router
         should drop an external BGP session immediately when the local
         interface goes down, or whether the BGP session should be kept up
         until the holdtime expires.

         A value of 'true' causes the external BGP session to go down
         immediately when the local interface goes down."
    DEFVAL      { false }
    ::= { tBgpPeerNgParamsEntry 2 }

tBgpPeerNgDisableComms           OBJECT-TYPE
    SYNTAX      TruthValue
    MAX-ACCESS  read-create
    STATUS      current
    DESCRIPTION
        "The value of tBgpPeerNgDisableComms enables or disables sending of
         community attribute to the peer for non-external communities."
    DEFVAL      { false }
    ::= { tBgpPeerNgParamsEntry 3 }

tBgpPeerNgDisableExtComms        OBJECT-TYPE
    SYNTAX      TruthValue
    MAX-ACCESS  read-create
    STATUS      current
    DESCRIPTION
        "The value of tBgpPeerNgDisableExtComms enables or disables sending of
         community attribute to the peers for external communities."
    DEFVAL      { false }
    ::= { tBgpPeerNgParamsEntry 4 }

tBgpPeerNgDefaultOriginate       OBJECT-TYPE
    SYNTAX      TmnxIpFamily
    MAX-ACCESS  read-create
    STATUS      current
    DESCRIPTION
        "The value of tBgpPeerNgDefaultOriginate specifies the types of
         AFI/SAFI for which SROS BGP will originate default route independent
         of the RTM default route."
    ::= { tBgpPeerNgParamsEntry 5 }

tBgpPeerNgAdvertiseInactiveRts   OBJECT-TYPE
    SYNTAX      TruthValue
    MAX-ACCESS  read-create
    STATUS      current
    DESCRIPTION
        "The value of tBgpPeerNgAdvertiseInactiveRts enables or disables
         advertising of inactive BGP routes to other BGP peers."
    DEFVAL      { false }
    ::= { tBgpPeerNgParamsEntry 6 }

tBgpPeerNgMinTTLValue            OBJECT-TYPE
    SYNTAX      Unsigned32 (0 | 1..255)
    MAX-ACCESS  read-create
    STATUS      current
    DESCRIPTION
        "The value of tBgpPeerNgMinTTLValue specifies the minimum TTL value for
         an incoming BGP packet.

         If tBgpPeerMinTTLValue is set to zero (0), the TTL Security feature is
         disabled."
    DEFVAL      { 0 }
    ::= { tBgpPeerNgParamsEntry 7 }

tBgpPeerNgTracking               OBJECT-TYPE
    SYNTAX      TruthValue
    MAX-ACCESS  read-create
    STATUS      current
    DESCRIPTION
        "The value of tBgpPeerNgTracking specifies whether tracking of this BGP
         peer is enabled.

         A value of 'false' indicates that peer tracking is disabled."
    DEFVAL      { false }
    ::= { tBgpPeerNgParamsEntry 8 }

tBgpPeerNgAdvLabelAddrFamily     OBJECT-TYPE
    SYNTAX      TmnxAdvLabelAddressFamily
    MAX-ACCESS  read-create
    STATUS      obsolete
    DESCRIPTION
        "The value of tBgpPeerNgAdvLabelAddrFamily specifies the advertisement
         label address family to support 6PE feature. The value of ipv6 can be
         set only for an IPv6 peer. The value of ipv4 can be set only for an
         IPv4 peer.

         If set to 'ipv6', explicit null will be used as the label. The default
         value 'none' disables the 6PE feature."
    ::= { tBgpPeerNgParamsEntry 9 }

tBgpPeerNgAuthKeyChain           OBJECT-TYPE
    SYNTAX      TNamedItemOrEmpty
    MAX-ACCESS  read-create
    STATUS      current
    DESCRIPTION
        "The value of tBgpPeerNgAuthKeyChain specifies the
         keychain which will be used to sign and/or authenticate  the BGP
         protocol stream.

         The keychain name is defined by tmnxKeyChainName and is the index for
         TIMETRA-SECURITY-MIB::tmnxKeyChainTable"
    DEFVAL      { ''H }
    ::= { tBgpPeerNgParamsEntry 10 }

tBgpPeerNgLastError              OBJECT-TYPE
    SYNTAX      OCTET STRING (SIZE (2))
    MAX-ACCESS  read-only
    STATUS      current
    DESCRIPTION
        "The value of tBgpPeerNgLastError indicates the last error code and
         subcode seen by this peer on this connection. If no error has
         occurred, two zero octets are returned. Otherwise, the first octet of
         this two-byte OCTET STRING contains the error code, and the second
         octet contains the subcode."
    ::= { tBgpPeerNgParamsEntry 11 }

tBgpPeerNgBfdEnabled             OBJECT-TYPE
    SYNTAX      TruthValue
    MAX-ACCESS  read-create
    STATUS      current
    DESCRIPTION
        "The value of tBgpPeerNgBfdEnabled specifies whether Bi-directional
         Forwarding Detection is enabled on this BGP peer.

         When the value is 'true', BFD sessions can be established and BFD can
         be used as a signalling mechanism."
    DEFVAL      { false }
    ::= { tBgpPeerNgParamsEntry 12 }

tBgpPeerNgPMTUDiscovery          OBJECT-TYPE
    SYNTAX      TruthValue
    MAX-ACCESS  read-create
    STATUS      current
    DESCRIPTION
        "The value of tBgpPeerNgPMTUDiscovery specifies whether path MTU
         discovery is enabled on this BGP peer.

         When the value is set to 'true', path MTU discovery is enabled on this
         BGP peer. When the value is set to 'false', path MTU discovery is
         disabled on this BGP peer."
    DEFVAL      { false }
    ::= { tBgpPeerNgParamsEntry 13 }

tBgpPeerNgAdvertiseLdpPrefix     OBJECT-TYPE
    SYNTAX      TruthValue
    MAX-ACCESS  read-create
    STATUS      current
    DESCRIPTION
        "The value of tBgpPeerNgAdvertiseLdpPrefix specifies whether all the
         activated LDP FEC prefixes will be sent to remote BGP peer to support
         stitching of an LDP FEC to a BGP labeled route.

         When the value is set to 'true', activated LDP FEC prefixes will be
         sent to remote BGP peer. When the value is set to 'false', activated
         LDP FEC prefixes will not be sent to remote BGP peer.

         An 'inconsistentValue' error is returned if this object is set to
         non-default value when tBgpPeerNgAdvLabelAddrFamily is set to 'none'."
    DEFVAL      { false }
    ::= { tBgpPeerNgParamsEntry 14 }

tBgpPeerNgEnableAddPath          OBJECT-TYPE
    SYNTAX      TruthValue
    MAX-ACCESS  read-create
    STATUS      obsolete
    DESCRIPTION
        "The value of tBgpPeerNgEnableAddPath specifies whether the BGP
         ADD-PATH send capability is enabled on this BGP peer.

         ADD-PATH allows a BGP router to advertise multiple distinct paths for
         the same prefix/NLRI(Network Layer Reachability Information). This
         capability provides a number of potential benefits like reduced
         routing churn, faster convergence, better loadsharing etc.

         When the value of tBgpPeerNgEnableAddPath is set to 'true', the BGP
         ADD-PATH send limit objects tBgpPeerNgIpv4AddPathLimit,
         tBgpPeerNgVpnIpv4AddPathLimit, tBgpPeerNgIpv6AddPathLimit,
         tBgpPeerNgVpnIpv6AddPathLimit, tBgpPeerNgLblIpv4AddPathLimit,
         tBgpPeerNgLblIpv6AddPathLimit represent their current assigned values.

         The default value of tBgpPeerNgEnableAddPath is 'false', which means
         the values of the BGP ADD-PATH send limit objects are inherited from
         group level."
    DEFVAL      { false }
    ::= { tBgpPeerNgParamsEntry 15 }

tBgpPeerNgRecvAddPath            OBJECT-TYPE
    SYNTAX      TmnxAddPathAddressFamily
    MAX-ACCESS  read-create
    STATUS      obsolete
    DESCRIPTION
        "The value of tBgpPeerNgRecvAddPath specifies the address families
         which are enabled to receive BGP ADD-PATH on this BGP peer.

         ADD-PATH allows a BGP router to receive multiple distinct paths for
         the same prefix/NLRI (Network Layer Reachability Information)."
    DEFVAL      { {none} }
    ::= { tBgpPeerNgParamsEntry 16 }

tBgpPeerNgIpv4AddPathLimit       OBJECT-TYPE
    SYNTAX      TmnxAddPathSendLimit
    MAX-ACCESS  read-create
    STATUS      obsolete
    DESCRIPTION
        "The value of tBgpPeerNgIpv4AddPathLimit specifies the maximum number
         of paths per IPv4 prefix that can be advertised to ADD-PATH peers on
         this BGP peer.

         An 'inconsistentValue' error is returned if an attempt is made to set
         this object to a value greater than tBgpInstanceMultipathBgp."
    DEFVAL      { 0 }
    ::= { tBgpPeerNgParamsEntry 17 }

tBgpPeerNgVpnIpv4AddPathLimit    OBJECT-TYPE
    SYNTAX      TmnxAddPathSendLimit
    MAX-ACCESS  read-create
    STATUS      obsolete
    DESCRIPTION
        "The value of tBgpPeerNgVpnIpv4AddPathLimit specifies the maximum
         number of paths per VPN IPv4 prefix that can be advertised to ADD-PATH
         peers on this BGP peer.

         An 'inconsistentValue' error is returned if an attempt is made to set
         this object to a value greater than tBgpInstanceMultipathBgp."
    DEFVAL      { 0 }
    ::= { tBgpPeerNgParamsEntry 18 }

tBgpPeerNgIpv6AddPathLimit       OBJECT-TYPE
    SYNTAX      TmnxAddPathSendLimit
    MAX-ACCESS  read-create
    STATUS      obsolete
    DESCRIPTION
        "The value of tBgpPeerNgIpv6AddPathLimit specifies the maximum number
         of paths per IPv6 prefix that can be advertised to ADD-PATH peers on
         this BGP peer.

         An 'inconsistentValue' error is returned if an attempt is made to set
         this object to a value greater than tBgpInstanceMultipathBgp."
    DEFVAL      { 0 }
    ::= { tBgpPeerNgParamsEntry 19 }

tBgpPeerNgVpnIpv6AddPathLimit    OBJECT-TYPE
    SYNTAX      TmnxAddPathSendLimit
    MAX-ACCESS  read-create
    STATUS      obsolete
    DESCRIPTION
        "The value of tBgpPeerNgVpnIpv6AddPathLimit specifies the maximum
         number of paths per VPN IPv6 prefix that can be advertised to ADD-PATH
         peers on this BGP peer.

         An 'inconsistentValue' error is returned if an attempt is made to set
         this object to a value greater than tBgpInstanceMultipath."
    DEFVAL      { 0 }
    ::= { tBgpPeerNgParamsEntry 20 }

tBgpPeerNgFlowspecValidate       OBJECT-TYPE
    SYNTAX      TruthValue
    MAX-ACCESS  read-create
    STATUS      obsolete
    DESCRIPTION
        "The value of tBgpPeerNgFlowspecValidate specifies whether validation
         of received flow specification routes is enabled on this BGP peer.

         When the default value of tBgpPeerNgFlowspecValidate is 'true', the
         flow routes received from other peers are validated.

         The default value of tBgpPeerNgFlowspecValidate is 'false', which
         means validation of received flow routes is disabled and all flow
         specification routes are considered valid."
    DEFVAL      { false }
    ::= { tBgpPeerNgParamsEntry 21 }

tBgpPeerNgUpdatedErrorHandling   OBJECT-TYPE
    SYNTAX      TruthValue
    MAX-ACCESS  read-create
    STATUS      obsolete
    DESCRIPTION
        "The value of tBgpPeerNgUpdatedErrorHandling specifies whether the
         error handling mechanism for optional transitive path attributes is
         enabled on this BGP peer.

         When the value of tBgpPeerNgUpdatedErrorHandling is 'true', the error
         handling mechanism for optional transitive path attributes is enabled
         and the BGP peer is capable of enabling the neighbor-complete flag in
         the BGP Path Attribute.

         This object is obsoleted in release 11.0."
    DEFVAL      { false }
    ::= { tBgpPeerNgParamsEntry 22 }

tBgpPeerNgDefaultRouteTarget     OBJECT-TYPE
    SYNTAX      TruthValue
    MAX-ACCESS  read-create
    STATUS      current
    DESCRIPTION
        "The value of tBgpPeerNgDefaultRouteTarget specifies whether to send
         the default Route Target Constraint (RTC) route to this BGP peer.

         The default RTC route is a special type of RTC route that has zero
         prefix length."
    DEFVAL      { false }
    ::= { tBgpPeerNgParamsEntry 23 }

tBgpPeerNgAigp                   OBJECT-TYPE
    SYNTAX      TruthValue
    MAX-ACCESS  read-create
    STATUS      current
    DESCRIPTION
        "The value of tBgpPeerNgAigp specifies whether Accumulated IGP (AIGP)
         path attribute support is enabled on this bgp peer.

         The default value of tBgpPeerNgAigp is 'false', which means the AIGP
         attribute is removed from the advertised routes and is ignored if
         present in the received routes."
    DEFVAL      { false }
    ::= { tBgpPeerNgParamsEntry 24 }

tBgpPeerNgMinHoldTime            OBJECT-TYPE
    SYNTAX      BgpHoldTime
    MAX-ACCESS  read-create
    STATUS      current
    DESCRIPTION
        "The value of tBgpPeerNgMinHoldTime specifies the minimum hold time
         that should be strictly enforced on tBgpPeerNgHoldTime.

         When the value of tBgpPeerNgMinHoldTime is configured, BGP will not
         negotiate a hold time lower than the configured value.

         When the value of tBgpPeerNgHoldTime is changed, the value of
         tBgpPeerNgMinHoldTime is reset to its default value.

         The value of tBgpPeerNgMinHoldTime is inherited from the corresponding
         object value in the tBgpPeerGroupParamsTable, when the inheritance bit
         for tBgpPeerNgHoldTime is set to zero. An 'inconsistentValue' error is
         returned if an attempt is made to set this object to a non-default
         value when the value of tBgpPeerNgHoldTime is inherited from group.

         An 'inconsistentValue' error is returned if an attempt is made to set
         this object to a value greater than tBgpPeerNgHoldTime."
    DEFVAL      { 0 }
    ::= { tBgpPeerNgParamsEntry 25 }

tBgpPeerNgSplitHorizon           OBJECT-TYPE
    SYNTAX      TruthValue
    MAX-ACCESS  read-create
    STATUS      current
    DESCRIPTION
        "The value of tBgpPeerNgSplitHorizon specifies whether or not to
         advertise the best route back to the same BGP peer from which the best
         route was received.

         When the value of tBgpPeerNgSplitHorizon is 'true', the peer will not
         reflect the best route to the peer from which the route was received."
    DEFVAL      { false }
    ::= { tBgpPeerNgParamsEntry 26 }

tBgpPeerNgRemPrivateSkipPeerAs   OBJECT-TYPE
    SYNTAX      TruthValue
    MAX-ACCESS  read-create
    STATUS      current
    DESCRIPTION
        "The value of tBgpPeerNgRemPrivateSkipPeerAs specifies whether or not
         to remove the private autonomous system number (ASN) from AS-Path, if
         the AS-Path contains the ASN of the external BGP (eBGP) neighbor on
         this BGP peer.

         When the value of tBgpPeerNgRemPrivateSkipPeerAs is true, BGP will not
         remove the private ASN from the AS-Path if it is the same autonomous
         system number as the remote eBGP peer."
    DEFVAL      { false }
    ::= { tBgpPeerNgParamsEntry 27 }

tBgpPeerNgLclASNoPrependGlobalAS OBJECT-TYPE
    SYNTAX      TruthValue
    MAX-ACCESS  read-create
    STATUS      current
    DESCRIPTION
        "The value of tBgpPeerNgLclASNoPrependGlobalAS specifies whether or not
         to prepend the global-AS when advertising routes to the external BGP
         (eBGP) neighbor on this BGP peer.

         When the value of tBgpPeerNgLclASNoPrependGlobalAS is true, BGP will
         prepend only the local-AS to the AS_PATH of received routes from the
         remote eBGP peer.

         When the value of tBgpPeerNgLocalAS4Byte is changed, the value of
         tBgpPeerNgLclASNoPrependGlobalAS is reset to its default value.

         An 'inconsistentValue' error is returned if an attempt is made to set
         this object to a non-default value when the value of object
         tBgpPeerNgLocalAS4Byte is not set to non-default value."
    DEFVAL      { false }
    ::= { tBgpPeerNgParamsEntry 28 }

tBgpPeerNgMaxPrefixIdleTimeOut   OBJECT-TYPE
    SYNTAX      Integer32 (0 | 1..1024)
    UNITS       "minutes"
    MAX-ACCESS  read-create
    STATUS      obsolete
    DESCRIPTION
        "The value of tBgpPeerNgMaxPrefixIdleTimeOut specifies the idle time in
         minutes that the BGP peering remains disabled before attempting to
         automatically re-establish the connection with this BGP peer after the
         tBgpPeerNgMaxPrefix limit is reached.

         The default value of tBgpPeerNgMaxPrefixIdleTimeOut is zero which
         means, no attempt will be made to re-establish the BGP peering with
         this BGP peer after tBgpPeerNgMaxPrefix limit is reached.

         When the value of tBgpPeerNgMaxPrefix is changed, the value of
         tBgpPeerNgMaxPrefixIdleTimeOut is reset to its default value.

         The value of tBgpPeerNgMaxPrefixIdleTimeOut is inherited from the
         corresponding object value in the tBgpPeerGroupParamsTable, when the
         inheritance bit for tBgpPeerNgMaxPrefix is set to zero. An
         'inconsistentValue' error is returned if an attempt is made to set
         this object to a non-default value when the value of
         tBgpPeerNgMaxPrefix is inherited from group.

         An 'inconsistentValue' error is returned if an attempt is made to set
         this object to a non-default value when the value of
         tBgpPeerNgMaxPrefixLogOnly is set to non-default value.

         This object was obsoleted in release 13.0."
    DEFVAL      { 0 }
    ::= { tBgpPeerNgParamsEntry 29 }

tBgpPeerNgGRRestartNotification  OBJECT-TYPE
    SYNTAX      TruthValue
    MAX-ACCESS  read-create
    STATUS      current
    DESCRIPTION
        "The value of tBgpPeerNgGRRestartNotification specifies whether or not
         to perform Graceful Restart procedures after sending or receiving a
         NOTIFICATION message on this BGP peer.

         When the value of tBgpPeerNgGRRestartNotification is true, BGP will
         perform Graceful Restart procedures after sending or receiving a
         NOTIFICATION on this BGP peer."
    DEFVAL      { false }
    ::= { tBgpPeerNgParamsEntry 30 }

tBgpPeerNgFaultTolerance         OBJECT-TYPE
    SYNTAX      TruthValue
    MAX-ACCESS  read-create
    STATUS      current
    DESCRIPTION
        "The value of tBgpPeerNgFaultTolerance specifies whether or not
         approaches like 'treat-as-withdraw' and other similar non-disruptive
         approaches can be used for handling a wide range of UPDATE message
         errors.

         A value of 'false' indicates that bgp fault-tolerance is disabled on
         this BGP peer."
    DEFVAL      { false }
    ::= { tBgpPeerNgParamsEntry 31 }

tBgpPeerNgDampPeerOscillations   OBJECT-TYPE
    SYNTAX      TruthValue
    MAX-ACCESS  read-create
    STATUS      current
    DESCRIPTION
        "The value of tBgpPeerNgDampPeerOscillations specifies whether damping
         peer oscillations is enabled for this BGP peer.

         When the value is set to 'true', damping peer oscillations is enabled
         for this BGP peer. When the value is set to 'false', damping peer
         oscillations is disabled."
    DEFVAL      { false }
    ::= { tBgpPeerNgParamsEntry 32 }

tBgpPeerNgDampOscInitialWaitTime OBJECT-TYPE
    SYNTAX      Unsigned32 (0..2048)
    UNITS       "minutes"
    MAX-ACCESS  read-create
    STATUS      current
    DESCRIPTION
        "The value of tBgpPeerNgDampOscInitialWaitTime specifies the time in
         minutes,that a session remains in the idle-state after it has been
         stable for a while for this BGP peer.

         When the value of tBgpPeerNgDampPeerOscillations is changed, the value
         of tBgpPeerNgDampOscInitialWaitTime is reset to its default value.

         The value of tBgpPeerNgDampOscInitialWaitTime is inherited from the
         corresponding object value in the tBgpPeerGroupParamsTable, when the
         inheritance bit for tBgpPeerNgDampPeerOscillations is set to zero. An
         'inconsistentValue' error is returned if an attempt is made to set
         this object to a non-default value when the value of
         tBgpPeerNgDampPeerOscillations is inherited from group.

         An 'inconsistentValue' error is returned if an attempt is made to set
         this object without setting tBgpPeerNgDampPeerOscillations."
    DEFVAL      { 0 }
    ::= { tBgpPeerNgParamsEntry 33 }

tBgpPeerNgDampOscSecondWaitTime  OBJECT-TYPE
    SYNTAX      Unsigned32 (1..2048)
    UNITS       "minutes"
    MAX-ACCESS  read-create
    STATUS      current
    DESCRIPTION
        "The value of tBgpPeerNgDampOscSecondWaitTime specifies the time in
         minutes, that is doubled after each repeated session failure that
         occurs within a relatively short span of time for this BGP peer.

         When the value of tBgpPeerNgDampPeerOscillations is changed, the value
         of tBgpPeerNgDampOscSecondWaitTime is reset to its default value.

         The value of tBgpPeerNgDampOscSecondWaitTime is inherited from the
         corresponding object value in the tBgpPeerGroupParamsTable, when the
         inheritance bit for tBgpPeerNgDampPeerOscillations is set to zero. An
         'inconsistentValue' error is returned if an attempt is made to set
         this object to a non-default value when the value of
         tBgpPeerNgDampPeerOscillations is inherited from group.

         An 'inconsistentValue' error is returned if an attempt is made to set
         this object without setting tBgpPeerNgDampPeerOscillations."
    DEFVAL      { 5 }
    ::= { tBgpPeerNgParamsEntry 34 }

tBgpPeerNgDampOscMaxWaitTime     OBJECT-TYPE
    SYNTAX      Unsigned32 (1..2048)
    UNITS       "minutes"
    MAX-ACCESS  read-create
    STATUS      current
    DESCRIPTION
        "The value of tBgpPeerNgDampOscMaxWaitTime specifies the maximum amount
         of time in minutes, that the session remains in the idle-state after
         it has experienced repeated instability for this BGP peer.

         When the value of tBgpPeerNgDampPeerOscillations is changed, the value
         of tBgpPeerNgDampOscMaxWaitTime is reset to its default value.

         The value of tBgpPeerNgDampOscMaxWaitTime is inherited from the
         corresponding object value in the tBgpPeerGroupParamsTable, when the
         inheritance bit for tBgpPeerNgDampPeerOscillations is set to zero. An
         'inconsistentValue' error is returned if an attempt is made to set
         this object to a non-default value when the value of
         tBgpPeerNgDampPeerOscillations is inherited from group.

         An 'inconsistentValue' error is returned if an attempt is made to set
         this object without setting tBgpPeerNgDampPeerOscillations."
    DEFVAL      { 60 }
    ::= { tBgpPeerNgParamsEntry 35 }

tBgpPeerNgDampOscErrorInterval   OBJECT-TYPE
    SYNTAX      Unsigned32 (0..2048)
    UNITS       "minutes"
    MAX-ACCESS  read-create
    STATUS      current
    DESCRIPTION
        "The value of tBgpPeerNgDampOscErrorInterval specifies the time in
         minutes after a session reset, during which the session must be
         error-free in order to reset the penalty counter and return
         idle-hold-time to tBgpPeerNgDampOscInitialWaitTime for this BGP peer.

         When the value of tBgpPeerNgDampPeerOscillations is changed, the value
         of tBgpPeerNgDampOscErrorInterval is reset to its default value.

         The value of tBgpPeerNgDampOscErrorInterval is inherited from the
         corresponding object value in the tBgpPeerGroupParamsTable, when the
         inheritance bit for tBgpPeerNgDampPeerOscillations is set to zero. An
         'inconsistentValue' error is returned if an attempt is made to set
         this object to a non-default value when the value of
         tBgpPeerNgDampPeerOscillations is inherited from group.

         An 'inconsistentValue' error is returned if an attempt is made to set
         this object without setting tBgpPeerNgDampPeerOscillations."
    DEFVAL      { 30 }
    ::= { tBgpPeerNgParamsEntry 36 }

tBgpPeerNgNhUnchangedFamily      OBJECT-TYPE
    SYNTAX      TmnxIpNhChgFamily
    MAX-ACCESS  read-create
    STATUS      current
    DESCRIPTION
        "The value of tBgpPeerNgNhUnchangedFamily specifies the address
         families for which the BGP next-hop is not modified when sending
         routes to selected EBGP peers in this peer.

         When the value of tBgpPeerNgNhUnchangedFamily is set to
         'labelIpv4',the next-hop attribute of an ebgp peer in this peer group
         remains unchanged.

         When the route is advertised to IBGP and confed-EBGP peers, the object
         tBgpPeerNgNhUnchangedFamily has no effect on the routes, since nexthop
         unchanged is default functionality.

         The value of tBgpPeerNgNhUnchangedFamily is inherited from the
         corresponding object value in the tBgpPeerGroupParamsTable, when the
         inheritance bit for tBgpPeerNgNhUnchangedFamily is set to zero. An
         'inconsistentValue' error is returned if an attempt is made to set
         this object to a non-default value when the value of
         tBgpPeerNgNhUnchangedFamily is inherited from group."
    DEFVAL      { {} }
    ::= { tBgpPeerNgParamsEntry 37 }

tBgpPeerNgEnableOriginValidation OBJECT-TYPE
    SYNTAX      TmnxIpFamily
    MAX-ACCESS  read-create
    STATUS      current
    DESCRIPTION
        "The value of tBgpPeerNgEnableOriginValidation specifies the address
         family for which every inbound IPv4 and/or IPv6 route from the peer is
         marked with either valid, not-found or invalid origin validation
         states.

         When the family of the received route matches the configured families
         in tBgpPeerNgEnableOriginValidation, the route is evaluated to
         determine its origin validation state.

         When the value of tBgpPeerNgEnableOriginValidation is not set to any
         corresponding family or when the value of
         tBgpPeerNgEnableOriginValidation is set to all families all unicast
         IPv4 and IPv6 routes are evaluated to determine their origin
         validation states."
    DEFVAL      { {} }
    ::= { tBgpPeerNgParamsEntry 38 }

tBgpPeerNgThirdPartyNextHop      OBJECT-TYPE
    SYNTAX      TruthValue
    MAX-ACCESS  read-create
    STATUS      current
    DESCRIPTION
        "The value of tBgpPeerNgThirdPartyNextHop specifies if there is any
         third party next-hop processing done towards this peer.

         When false, NEXT_HOP will always carry the IP address of the interface
         used to establish the TCP connection to the peer"
    DEFVAL      { false }
    ::= { tBgpPeerNgParamsEntry 39 }

tBgpPeerNgAddLinkBandwidth       OBJECT-TYPE
    SYNTAX      TmnxIpFamily
    MAX-ACCESS  read-create
    STATUS      current
    DESCRIPTION
        "The value of tBgpPeerNgAddLinkBandwidth specifies the address families
         of the routes received from a single-hop EBGP neighbor, for which a
         Link Bandwidth Extended Community with static AS and bandwidth values
         is added.

         When the family of the received route matches the configured families
         in tBgpPeerNgAddLinkBandwidth, a Link Bandwidth Extended Community is
         added, consisting of the local AS and interface speed."
    DEFVAL      { {} }
    ::= { tBgpPeerNgParamsEntry 40 }

tBgpPeerNgDefRxEvpnEncap         OBJECT-TYPE
    SYNTAX      INTEGER {
        mpls  (0),
        vxlan (1)
    }
    MAX-ACCESS  read-create
    STATUS      current
    DESCRIPTION
        "The value of tBgpPeerNgDefRxEvpnEncap specifies how BGP will treat a
         received EVPN route without BGP encapsulation extended community. If
         no encapsulation is received, BGP will validate the route as MPLS or
         VXLAN depending on the the value of tBgpPeerNgDefRxEvpnEncap."
    DEFVAL      { mpls }
    ::= { tBgpPeerNgParamsEntry 41 }

tBgpPeerNgLabelResolveStatic     OBJECT-TYPE
    SYNTAX      TruthValue
    MAX-ACCESS  read-create
    STATUS      obsolete
    DESCRIPTION
        "The value of tBgpPeerNgLabelResolveStatic specifies whether for an
         eBGP peer if enabled, allows only labeled BGP routes learned from the
         associated eBGP peer to be resolved via the IP routes.

         Even if this behavior is enabled, LDP or RSVP-TE defined paths should
         first resolve the BGP nexthop for the labeled routes. Only if none are
         available should resolution to the IP route table be attempted."
    DEFVAL      { false }
    ::= { tBgpPeerNgParamsEntry 42 }

tBgpPeerNgLblIpv4AddPathLimit    OBJECT-TYPE
    SYNTAX      TmnxAddPathSendLimit
    MAX-ACCESS  read-create
    STATUS      obsolete
    DESCRIPTION
        "The value of tBgpPeerNgLblIpv4AddPathLimit specifies the maximum
         number of paths per label IPv4 prefix that can be advertised to
         ADD-PATH peers on this BGP peer.

         An 'inconsistentValue' error is returned if an attempt is made to set
         this object to a value greater than tBgpInstanceMultipathBgp."
    DEFVAL      { 0 }
    ::= { tBgpPeerNgParamsEntry 43 }

tBgpPeerNgLblIpv6AddPathLimit    OBJECT-TYPE
    SYNTAX      TmnxAddPathSendLimit
    MAX-ACCESS  read-create
    STATUS      obsolete
    DESCRIPTION
        "The value of tBgpPeerNgLblIpv6AddPathLimit specifies the maximum
         number of paths per label IPv6 prefix that can be advertised to
         ADD-PATH peers on this BGP peer.

         An 'inconsistentValue' error is returned if an attempt is made to set
         this object to a value greater than tBgpInstanceMultipathBgp."
    DEFVAL      { 0 }
    ::= { tBgpPeerNgParamsEntry 44 }

tBgpPeerNgLabelPreference        OBJECT-TYPE
    SYNTAX      TmnxBgpPreference (1..255)
    MAX-ACCESS  read-create
    STATUS      current
    DESCRIPTION
        "The value of tBgpPeerNgLabelPreference specifies the route preference
         for label-IPv4 and label-IPv6 routes learned via the peer."
    DEFVAL      { 170 }
    ::= { tBgpPeerNgParamsEntry 45 }

tBgpPeerNgORRLocation            OBJECT-TYPE
    SYNTAX      Unsigned32 (0..255)
    MAX-ACCESS  read-create
    STATUS      current
    DESCRIPTION
        "The value of tBgpPeerNgORRLocation specifies the identifier of a
         location configured under optimal-route-reflection. The location is
         used to calculate the next-hop cost in the TE-DB and select the best
         path to advertise to the client of this route-reflector."
    DEFVAL      { 0 }
    ::= { tBgpPeerNgParamsEntry 46 }

tBgpPeerNgORRAllowLocalFallbk    OBJECT-TYPE
    SYNTAX      TruthValue
    MAX-ACCESS  read-create
    STATUS      current
    DESCRIPTION
        "The value of tBgpPeerNgORRAllowLocalFallbk decides what the system
         should do when the BGP next-hop is not reachable in the TE-DB for the
         configured location, tBgpPeerNgORRLocation.

         If the value is set to 'true', then next-hop cost calculation and
         best-path selection default back to the location of the
         route-reflector in the network.

         If the value is set to 'false', then no routes are advertised to the
         client(s)."
    DEFVAL      { false }
    ::= { tBgpPeerNgParamsEntry 47 }

tBgpPeerNgEnforceFirstAS         OBJECT-TYPE
    SYNTAX      TruthValue
    MAX-ACCESS  read-create
    STATUS      current
    DESCRIPTION
        "The value of tBgpPeerNgEnforceFirstAS specifies whether the receipt of
         BGP routes from an eBGP neighbor should be classified as an error when
         it has an AS-Path with the most recent AS not matching the configured
         peer-as of the neighbor.

         If the value is set to 'true', the most recent AS number in the
         AS-Path will be checked for every received route from the peer or set
         of peers to match the peer's configured peer-as. If it does not match,
         then the session will be reset if the update-fault-tolerance under
         error-handling is not configured. Else, the session will not be reset,
         but all the prefixes in the received update will be treated as
         withdrawn and logged.

         It is applicable to all the address families and only to true eBGP
         sessions."
    DEFVAL      { false }
    ::= { tBgpPeerNgParamsEntry 48 }

tBgpPeerNgMvpnIpv4AddPathLimit   OBJECT-TYPE
    SYNTAX      Integer32 (0..16)
    MAX-ACCESS  read-create
    STATUS      obsolete
    DESCRIPTION
        "The value of tBgpPeerNgMvpnIpv4AddPathLimit specifies the maximum
         number of paths per MVPN IPv4 prefix that can be advertised to
         ADD-PATH peers on this BGP peer.

         An 'inconsistentValue' error is returned if an attempt is made to set
         this object to a value greater than tBgpInstanceMultipathBgp."
    DEFVAL      { 0 }
    ::= { tBgpPeerNgParamsEntry 49 }

tBgpPeerNgMvpnIpv6AddPathLimit   OBJECT-TYPE
    SYNTAX      Integer32 (0..16)
    MAX-ACCESS  read-create
    STATUS      obsolete
    DESCRIPTION
        "The value of tBgpPeerNgMvpnIpv6AddPathLimit specifies the maximum
         number of paths per MVPN IPv6 prefix that can be advertised to
         ADD-PATH peers on this BGP peer.

         An 'inconsistentValue' error is returned if an attempt is made to set
         this object to a value greater than tBgpInstanceMultipathBgp."
    DEFVAL      { 0 }
    ::= { tBgpPeerNgParamsEntry 50 }

tBgpPeerNgMcastVpnV4AddPathLimit OBJECT-TYPE
    SYNTAX      Integer32 (0..16)
    MAX-ACCESS  read-create
    STATUS      obsolete
    DESCRIPTION
        "The value of tBgpPeerNgMcastVpnV4AddPathLimit specifies the maximum
         number of paths per Mcast VPN IPv4 prefix that can be advertised to
         ADD-PATH peers on this BGP peer.

         An 'inconsistentValue' error is returned if an attempt is made to set
         this object to a value greater than tBgpInstanceMultipathBgp."
    DEFVAL      { 0 }
    ::= { tBgpPeerNgParamsEntry 51 }

tBgpPeerNgMcastVpnV6AddPathLimit OBJECT-TYPE
    SYNTAX      Integer32 (0..16)
    MAX-ACCESS  read-create
    STATUS      obsolete
    DESCRIPTION
        "The value of tBgpPeerNgMcastVpnV6AddPathLimit specifies the maximum
         number of paths per Mcast VPN IPv6 prefix that can be advertised to
         ADD-PATH peers on this BGP peer.

         An 'inconsistentValue' error is returned if an attempt is made to set
         this object to a value greater than tBgpInstanceMultipath."
    DEFVAL      { 0 }
    ::= { tBgpPeerNgParamsEntry 52 }

tBgpPeerLLGRAdvStaleTime         OBJECT-TYPE
    SYNTAX      Unsigned32 (0..16777215)
    UNITS       "seconds"
    MAX-ACCESS  read-create
    STATUS      current
    DESCRIPTION
        "The value of tBgpPeerLLGRAdvStaleTime specifies the time value until
         when a route can be used after the session with the peer is
         disconnected"
    DEFVAL      { 86400 }
    ::= { tBgpPeerNgParamsEntry 53 }

tBgpPeerLLGROvrideStaleTime      OBJECT-TYPE
    SYNTAX      Unsigned32 (0..16777216)
    UNITS       "seconds"
    MAX-ACCESS  read-create
    STATUS      current
    DESCRIPTION
        "The value of tBgpPeerLLGROvrideStaleTime specifies the stale time for
         the BGP session when it is in helper mode."
    DEFVAL      { 16777216 }
    ::= { tBgpPeerNgParamsEntry 54 }

tBgpPeerLLGROvrideResTime        OBJECT-TYPE
    SYNTAX      Unsigned32 (0..4096)
    UNITS       "seconds"
    MAX-ACCESS  read-create
    STATUS      current
    DESCRIPTION
        "The value of tBgpPeerLLGROvrideResTime specifies the restart time for
         the BGP session when it is in helper mode."
    DEFVAL      { 4096 }
    ::= { tBgpPeerNgParamsEntry 55 }

tBgpPeerLLGRFwdingBitsSet        OBJECT-TYPE
    SYNTAX      INTEGER {
        none    (0),
        all     (1),
        non-fwd (2)
    }
    MAX-ACCESS  read-create
    STATUS      current
    DESCRIPTION
        "The value of tBgpPeerLLGRFwdingBitsSet specifies the behaviour of the
         F bit for each AFI/SAFI."
    DEFVAL      { none }
    ::= { tBgpPeerNgParamsEntry 56 }

tBgpPeerLLGRAdvStaleToNeigh      OBJECT-TYPE
    SYNTAX      TruthValue
    MAX-ACCESS  read-create
    STATUS      current
    DESCRIPTION
        "The value of tBgpPeerLLGRAdvStaleToNeigh decides whether to withdraw
         the route towards eBGP peers that did not advertise the LLGR
         capability and re-advertise to all other peers with the addition of
         the LLGR_STALE community."
    DEFVAL      { false }
    ::= { tBgpPeerNgParamsEntry 57 }

tBgpPeerLLGRAdvToNeighWthoutNoEx OBJECT-TYPE
    SYNTAX      TruthValue
    MAX-ACCESS  read-create
    STATUS      current
    DESCRIPTION
        "The value of tBgpPeerLLGRAdvToNeighWthoutNoEx decides whether to
         advertise the route to all peers with the addition of the LLGR_STALE
         community.

         This can be configured only when tBgpPeerLLGRAdvStaleToNeigh is
         configured on the system."
    DEFVAL      { false }
    ::= { tBgpPeerNgParamsEntry 58 }

tBgpPeerLLGR                     OBJECT-TYPE
    SYNTAX      TruthValue
    MAX-ACCESS  read-create
    STATUS      current
    DESCRIPTION
        "The value of tBgpPeerLLGR specifies whether or not long lived graceful
         restart capabilities are enabled on this instance of BGP.

         When the value is set to 'false' long lived graceful restart is
         disabled and any previous configuration of other long lived graceful
         restart parameters is removed."
    DEFVAL      { false }
    ::= { tBgpPeerNgParamsEntry 59 }

tBgpPeerLocalAddressIfName       OBJECT-TYPE
    SYNTAX      TNamedItemOrEmpty
    MAX-ACCESS  read-create
    STATUS      current
    DESCRIPTION
        "The value of tBgpPeerLocalAddressIfName specifies the local interface
         name that the peer is to use as advertisement source address."
    ::= { tBgpPeerNgParamsEntry 60 }

tBgpPeerAdvIpv6NhFamily          OBJECT-TYPE
    SYNTAX      TmnxIpFamily
    MAX-ACCESS  read-create
    STATUS      current
    DESCRIPTION
        "The value of tBgpPeerAdvIpv6NhFamily specifies the types of AFI/SAFI
         the SROS BGP peer supports extended next-hop encoding and resolution."
    ::= { tBgpPeerNgParamsEntry 61 }

tBgpPeerExtendNhEncoding         OBJECT-TYPE
    SYNTAX      TmnxIpFamily
    MAX-ACCESS  read-create
    STATUS      current
    DESCRIPTION
        "The value of tBgpPeerExtendNhEncoding specifies the types of AFI/SAFI
         the Bgp peer is configured to support extended next-hop encoding."
    ::= { tBgpPeerNgParamsEntry 62 }

tBgpPeerBypassMRAITimer          OBJECT-TYPE
    SYNTAX      TruthValue
    MAX-ACCESS  read-create
    STATUS      current
    DESCRIPTION
        "The value of tBgpPeerBypassMRAITimer specifies whether the Bgp
         instance is configured to send out the BGP update immediately after
         the session comes up, without waiting for Minimum Route Advertisement
         Interval, tBgpPeerNgMinRouteAdvertisement, to countdown to zero.

         If the value is set to 'true', tBgpPeerNgMinRouteAdvertisement's value
         is disregarded and BGP updates are sent out immediately after the
         session comes up.

         If the value is set to 'false', the system waits for
         tBgpPeerNgMinRouteAdvertisement's full value to countdown before
         sending out the BGP updates after the session comes up."
    DEFVAL      { false }
    ::= { tBgpPeerNgParamsEntry 63 }

tBgpPeerNgEvpnAddPathLimit       OBJECT-TYPE
    SYNTAX      TmnxAddPathSendLimit
    MAX-ACCESS  read-create
    STATUS      obsolete
    DESCRIPTION
        "The value of tBgpPeerNgEvpnAddPathLimit specifies the maximum number
         of paths per MVPN IPv4 prefix that can be advertised to ADD-PATH peers
         on this BGP peer.

         An 'inconsistentValue' error is returned if an attempt is made to set
         this object to a value greater than tBgpInstanceMultipathBgp."
    DEFVAL      { 0 }
    ::= { tBgpPeerNgParamsEntry 64 }

tBgpPeerPlcyTable                OBJECT-TYPE
    SYNTAX      SEQUENCE OF TBgpPeerPlcyEntry
    MAX-ACCESS  not-accessible
    STATUS      current
    DESCRIPTION
        "The tBgpPeerPlcyTable is the list of configured policies in BGP Peers."
    ::= { tBgpPeerObjects 11 }

tBgpPeerPlcyEntry                OBJECT-TYPE
    SYNTAX      TBgpPeerPlcyEntry
    MAX-ACCESS  not-accessible
    STATUS      current
    DESCRIPTION
        "An entry (conceptual row) in the tBgpPeerPlcyTable."
    AUGMENTS    { tBgpPeerNgEntry }
    ::= { tBgpPeerPlcyTable 1 }

TBgpPeerPlcyEntry                ::= SEQUENCE
{
    tBgpPeerPlcyImportPolicy1        TXLPolicyNameOrExpOrEmpty,
    tBgpPeerPlcyImportPolicy2        TLPolicyNameOrExpOrEmpty,
    tBgpPeerPlcyImportPolicy3        TLPolicyNameOrExpOrEmpty,
    tBgpPeerPlcyImportPolicy4        TLPolicyNameOrExpOrEmpty,
    tBgpPeerPlcyImportPolicy5        TLPolicyNameOrExpOrEmpty,
    tBgpPeerPlcyImportPolicy6        TLPolicyNameOrExpOrEmpty,
    tBgpPeerPlcyImportPolicy7        TLPolicyNameOrExpOrEmpty,
    tBgpPeerPlcyImportPolicy8        TLPolicyNameOrExpOrEmpty,
    tBgpPeerPlcyImportPolicy9        TLPolicyNameOrExpOrEmpty,
    tBgpPeerPlcyImportPolicy10       TLPolicyNameOrExpOrEmpty,
    tBgpPeerPlcyImportPolicy11       TLPolicyNameOrExpOrEmpty,
    tBgpPeerPlcyImportPolicy12       TLPolicyNameOrExpOrEmpty,
    tBgpPeerPlcyImportPolicy13       TLPolicyNameOrExpOrEmpty,
    tBgpPeerPlcyImportPolicy14       TLPolicyNameOrExpOrEmpty,
    tBgpPeerPlcyImportPolicy15       TLPolicyNameOrExpOrEmpty,
    tBgpPeerPlcyExportPolicy1        TXLPolicyNameOrExpOrEmpty,
    tBgpPeerPlcyExportPolicy2        TLPolicyNameOrExpOrEmpty,
    tBgpPeerPlcyExportPolicy3        TLPolicyNameOrExpOrEmpty,
    tBgpPeerPlcyExportPolicy4        TLPolicyNameOrExpOrEmpty,
    tBgpPeerPlcyExportPolicy5        TLPolicyNameOrExpOrEmpty,
    tBgpPeerPlcyExportPolicy6        TLPolicyNameOrExpOrEmpty,
    tBgpPeerPlcyExportPolicy7        TLPolicyNameOrExpOrEmpty,
    tBgpPeerPlcyExportPolicy8        TLPolicyNameOrExpOrEmpty,
    tBgpPeerPlcyExportPolicy9        TLPolicyNameOrExpOrEmpty,
    tBgpPeerPlcyExportPolicy10       TLPolicyNameOrExpOrEmpty,
    tBgpPeerPlcyExportPolicy11       TLPolicyNameOrExpOrEmpty,
    tBgpPeerPlcyExportPolicy12       TLPolicyNameOrExpOrEmpty,
    tBgpPeerPlcyExportPolicy13       TLPolicyNameOrExpOrEmpty,
    tBgpPeerPlcyExportPolicy14       TLPolicyNameOrExpOrEmpty,
    tBgpPeerPlcyExportPolicy15       TLPolicyNameOrExpOrEmpty
}

tBgpPeerPlcyImportPolicy1        OBJECT-TYPE
    SYNTAX      TXLPolicyNameOrExpOrEmpty
    MAX-ACCESS  read-create
    STATUS      current
    DESCRIPTION
        "The value of tBgpPeerPlcyImportPolicy1 specifies the first import
         policy."
    DEFVAL      { ''H }
    ::= { tBgpPeerPlcyEntry 1 }

tBgpPeerPlcyImportPolicy2        OBJECT-TYPE
    SYNTAX      TLPolicyNameOrExpOrEmpty
    MAX-ACCESS  read-create
    STATUS      current
    DESCRIPTION
        "The value of tBgpPeerPlcyImportPolicy2 specifies the second import
         policy."
    DEFVAL      { ''H }
    ::= { tBgpPeerPlcyEntry 2 }

tBgpPeerPlcyImportPolicy3        OBJECT-TYPE
    SYNTAX      TLPolicyNameOrExpOrEmpty
    MAX-ACCESS  read-create
    STATUS      current
    DESCRIPTION
        "The value of tBgpPeerPlcyImportPolicy3 specifies the third import
         policy."
    DEFVAL      { ''H }
    ::= { tBgpPeerPlcyEntry 3 }

tBgpPeerPlcyImportPolicy4        OBJECT-TYPE
    SYNTAX      TLPolicyNameOrExpOrEmpty
    MAX-ACCESS  read-create
    STATUS      current
    DESCRIPTION
        "The value of tBgpPeerPlcyImportPolicy4 specifies the fourth import
         policy."
    DEFVAL      { ''H }
    ::= { tBgpPeerPlcyEntry 4 }

tBgpPeerPlcyImportPolicy5        OBJECT-TYPE
    SYNTAX      TLPolicyNameOrExpOrEmpty
    MAX-ACCESS  read-create
    STATUS      current
    DESCRIPTION
        "The value of tBgpPeerPlcyImportPolicy5 specifies the fifth import
         policy."
    DEFVAL      { ''H }
    ::= { tBgpPeerPlcyEntry 5 }

tBgpPeerPlcyImportPolicy6        OBJECT-TYPE
    SYNTAX      TLPolicyNameOrExpOrEmpty
    MAX-ACCESS  read-create
    STATUS      current
    DESCRIPTION
        "The value of tBgpPeerPlcyImportPolicy6 specifies the sixth import
         policy."
    DEFVAL      { ''H }
    ::= { tBgpPeerPlcyEntry 6 }

tBgpPeerPlcyImportPolicy7        OBJECT-TYPE
    SYNTAX      TLPolicyNameOrExpOrEmpty
    MAX-ACCESS  read-create
    STATUS      current
    DESCRIPTION
        "The value of tBgpPeerPlcyImportPolicy7 specifies the seventh import
         policy."
    DEFVAL      { ''H }
    ::= { tBgpPeerPlcyEntry 7 }

tBgpPeerPlcyImportPolicy8        OBJECT-TYPE
    SYNTAX      TLPolicyNameOrExpOrEmpty
    MAX-ACCESS  read-create
    STATUS      current
    DESCRIPTION
        "The value of tBgpPeerPlcyImportPolicy8 specifies the eighth import
         policy."
    DEFVAL      { ''H }
    ::= { tBgpPeerPlcyEntry 8 }

tBgpPeerPlcyImportPolicy9        OBJECT-TYPE
    SYNTAX      TLPolicyNameOrExpOrEmpty
    MAX-ACCESS  read-create
    STATUS      current
    DESCRIPTION
        "The value of tBgpPeerPlcyImportPolicy9 specifies the ninth import
         policy."
    DEFVAL      { ''H }
    ::= { tBgpPeerPlcyEntry 9 }

tBgpPeerPlcyImportPolicy10       OBJECT-TYPE
    SYNTAX      TLPolicyNameOrExpOrEmpty
    MAX-ACCESS  read-create
    STATUS      current
    DESCRIPTION
        "The value of tBgpPeerPlcyImportPolicy10 specifies the tenth import
         policy."
    DEFVAL      { ''H }
    ::= { tBgpPeerPlcyEntry 10 }

tBgpPeerPlcyImportPolicy11       OBJECT-TYPE
    SYNTAX      TLPolicyNameOrExpOrEmpty
    MAX-ACCESS  read-create
    STATUS      current
    DESCRIPTION
        "The value of tBgpPeerPlcyImportPolicy11 specifies the eleventh import
         policy."
    DEFVAL      { ''H }
    ::= { tBgpPeerPlcyEntry 11 }

tBgpPeerPlcyImportPolicy12       OBJECT-TYPE
    SYNTAX      TLPolicyNameOrExpOrEmpty
    MAX-ACCESS  read-create
    STATUS      current
    DESCRIPTION
        "The value of tBgpPeerPlcyImportPolicy12 specifies the twelfth import
         policy."
    DEFVAL      { ''H }
    ::= { tBgpPeerPlcyEntry 12 }

tBgpPeerPlcyImportPolicy13       OBJECT-TYPE
    SYNTAX      TLPolicyNameOrExpOrEmpty
    MAX-ACCESS  read-create
    STATUS      current
    DESCRIPTION
        "The value of tBgpPeerPlcyImportPolicy13 specifies the thirteenth
         import policy."
    DEFVAL      { ''H }
    ::= { tBgpPeerPlcyEntry 13 }

tBgpPeerPlcyImportPolicy14       OBJECT-TYPE
    SYNTAX      TLPolicyNameOrExpOrEmpty
    MAX-ACCESS  read-create
    STATUS      current
    DESCRIPTION
        "The value of tBgpPeerPlcyImportPolicy14 specifies the fourteenth
         import policy."
    DEFVAL      { ''H }
    ::= { tBgpPeerPlcyEntry 14 }

tBgpPeerPlcyImportPolicy15       OBJECT-TYPE
    SYNTAX      TLPolicyNameOrExpOrEmpty
    MAX-ACCESS  read-create
    STATUS      current
    DESCRIPTION
        "The value of tBgpPeerPlcyImportPolicy15 specifies the fifteenth import
         policy."
    DEFVAL      { ''H }
    ::= { tBgpPeerPlcyEntry 15 }

tBgpPeerPlcyExportPolicy1        OBJECT-TYPE
    SYNTAX      TXLPolicyNameOrExpOrEmpty
    MAX-ACCESS  read-create
    STATUS      current
    DESCRIPTION
        "The value of tBgpPeerPlcyExportPolicy1 specifies the first export
         policy."
    DEFVAL      { ''H }
    ::= { tBgpPeerPlcyEntry 16 }

tBgpPeerPlcyExportPolicy2        OBJECT-TYPE
    SYNTAX      TLPolicyNameOrExpOrEmpty
    MAX-ACCESS  read-create
    STATUS      current
    DESCRIPTION
        "The value of tBgpPeerPlcyExportPolicy2 specifies the second export
         policy."
    DEFVAL      { ''H }
    ::= { tBgpPeerPlcyEntry 17 }

tBgpPeerPlcyExportPolicy3        OBJECT-TYPE
    SYNTAX      TLPolicyNameOrExpOrEmpty
    MAX-ACCESS  read-create
    STATUS      current
    DESCRIPTION
        "The value of tBgpPeerPlcyExportPolicy3 specifies the third export
         policy."
    DEFVAL      { ''H }
    ::= { tBgpPeerPlcyEntry 18 }

tBgpPeerPlcyExportPolicy4        OBJECT-TYPE
    SYNTAX      TLPolicyNameOrExpOrEmpty
    MAX-ACCESS  read-create
    STATUS      current
    DESCRIPTION
        "The value of tBgpPeerPlcyExportPolicy4 specifies the fourth export
         policy."
    DEFVAL      { ''H }
    ::= { tBgpPeerPlcyEntry 19 }

tBgpPeerPlcyExportPolicy5        OBJECT-TYPE
    SYNTAX      TLPolicyNameOrExpOrEmpty
    MAX-ACCESS  read-create
    STATUS      current
    DESCRIPTION
        "The value of tBgpPeerPlcyExportPolicy5 specifies the fifth export
         policy."
    DEFVAL      { ''H }
    ::= { tBgpPeerPlcyEntry 20 }

tBgpPeerPlcyExportPolicy6        OBJECT-TYPE
    SYNTAX      TLPolicyNameOrExpOrEmpty
    MAX-ACCESS  read-create
    STATUS      current
    DESCRIPTION
        "The value of tBgpPeerPlcyExportPolicy6 specifies the sixth export
         policy."
    DEFVAL      { ''H }
    ::= { tBgpPeerPlcyEntry 21 }

tBgpPeerPlcyExportPolicy7        OBJECT-TYPE
    SYNTAX      TLPolicyNameOrExpOrEmpty
    MAX-ACCESS  read-create
    STATUS      current
    DESCRIPTION
        "The value of tBgpPeerPlcyExportPolicy7 specifies the seventh export
         policy."
    DEFVAL      { ''H }
    ::= { tBgpPeerPlcyEntry 22 }

tBgpPeerPlcyExportPolicy8        OBJECT-TYPE
    SYNTAX      TLPolicyNameOrExpOrEmpty
    MAX-ACCESS  read-create
    STATUS      current
    DESCRIPTION
        "The value of tBgpPeerPlcyExportPolicy8 specifies the eighth export
         policy."
    DEFVAL      { ''H }
    ::= { tBgpPeerPlcyEntry 23 }

tBgpPeerPlcyExportPolicy9        OBJECT-TYPE
    SYNTAX      TLPolicyNameOrExpOrEmpty
    MAX-ACCESS  read-create
    STATUS      current
    DESCRIPTION
        "The value of tBgpPeerPlcyExportPolicy9 specifies the ninth export
         policy."
    DEFVAL      { ''H }
    ::= { tBgpPeerPlcyEntry 24 }

tBgpPeerPlcyExportPolicy10       OBJECT-TYPE
    SYNTAX      TLPolicyNameOrExpOrEmpty
    MAX-ACCESS  read-create
    STATUS      current
    DESCRIPTION
        "The value of tBgpPeerPlcyExportPolicy10 specifies the tenth export
         policy."
    DEFVAL      { ''H }
    ::= { tBgpPeerPlcyEntry 25 }

tBgpPeerPlcyExportPolicy11       OBJECT-TYPE
    SYNTAX      TLPolicyNameOrExpOrEmpty
    MAX-ACCESS  read-create
    STATUS      current
    DESCRIPTION
        "The value of tBgpPeerPlcyExportPolicy11 specifies the eleventh export
         policy."
    DEFVAL      { ''H }
    ::= { tBgpPeerPlcyEntry 26 }

tBgpPeerPlcyExportPolicy12       OBJECT-TYPE
    SYNTAX      TLPolicyNameOrExpOrEmpty
    MAX-ACCESS  read-create
    STATUS      current
    DESCRIPTION
        "The value of tBgpPeerPlcyExportPolicy12 specifies the twelfth export
         policy."
    DEFVAL      { ''H }
    ::= { tBgpPeerPlcyEntry 27 }

tBgpPeerPlcyExportPolicy13       OBJECT-TYPE
    SYNTAX      TLPolicyNameOrExpOrEmpty
    MAX-ACCESS  read-create
    STATUS      current
    DESCRIPTION
        "The value of tBgpPeerPlcyExportPolicy13 specifies the thirteenth
         export policy."
    DEFVAL      { ''H }
    ::= { tBgpPeerPlcyEntry 28 }

tBgpPeerPlcyExportPolicy14       OBJECT-TYPE
    SYNTAX      TLPolicyNameOrExpOrEmpty
    MAX-ACCESS  read-create
    STATUS      current
    DESCRIPTION
        "The value of tBgpPeerPlcyExportPolicy14 specifies the fourteenth
         export policy."
    DEFVAL      { ''H }
    ::= { tBgpPeerPlcyEntry 29 }

tBgpPeerPlcyExportPolicy15       OBJECT-TYPE
    SYNTAX      TLPolicyNameOrExpOrEmpty
    MAX-ACCESS  read-create
    STATUS      current
    DESCRIPTION
        "The value of tBgpPeerPlcyExportPolicy15 specifies the fifteenth export
         policy."
    DEFVAL      { ''H }
    ::= { tBgpPeerPlcyEntry 30 }

tBgpPeerNgPfxLmtTableLstChgd     OBJECT-TYPE
    SYNTAX      TimeStamp
    MAX-ACCESS  read-only
    STATUS      current
    DESCRIPTION
        "The value of tBgpPeerNgPfxLmtTableLstChgd indicates the time of the
         last change to any row of tBgpPeerNgPfxLmtTable."
    ::= { tBgpPeerObjects 12 }

tBgpPeerNgPfxLmtTable            OBJECT-TYPE
    SYNTAX      SEQUENCE OF TBgpPeerNgPfxLmtEntry
    MAX-ACCESS  not-accessible
    STATUS      current
    DESCRIPTION
        "The tBgpPeerNgPfxLmtTable is the list of configured prefix limits for
         different family types for BGP IPV4 and IPV6 peers.

         The table entries are indexed by BGP instance, peer address type and
         the peer's IP address and family type. For administrative convenience
         the peer group name should be set but is not used for sorting in the
         agent."
    ::= { tBgpPeerObjects 13 }

tBgpPeerNgPfxLmtEntry            OBJECT-TYPE
    SYNTAX      TBgpPeerNgPfxLmtEntry
    MAX-ACCESS  not-accessible
    STATUS      current
    DESCRIPTION
        "Defines an entry (conceptual row) in the tBgpPeerNgPfxLmtTable.

         An entry can be created using the row status object,
         tBgpPeerNgPfxLmtRowStatus. When created, all objects are initialized
         to their default values.

         Before the peer entry can be used, tBgpPeerNgPfxLmtRowStatus
         must be set to 'active(1)'.  the Peer entry can be removed
         by setting tBgpPeerNgPfxLmtRowStatus to 'destroy(6)'."
    INDEX       {
        tBgpPeerNgInstanceIndex,
        tBgpPeerNgAddressType,
        tBgpPeerNgAddress,
        tBgpPeerNgPfxLmtFamily
    }
    ::= { tBgpPeerNgPfxLmtTable 1 }

TBgpPeerNgPfxLmtEntry            ::= SEQUENCE
{
    tBgpPeerNgPfxLmtFamily           TmnxIpFamilyIdentifier,
    tBgpPeerNgPfxLmtLastChanged      TimeStamp,
    tBgpPeerNgPfxLmtRowStatus        RowStatus,
    tBgpPeerNgPfxLmtMaxPrefix        BgpPrefixLimit,
    tBgpPeerNgPfxLmtLogOnly          TruthValue,
    tBgpPeerNgPfxLmtThreshold        Unsigned32,
    tBgpPeerNgPfxLmtIdleTimeOut      Integer32,
    tBgpPeerNgPfxLmtPostImport       TruthValue,
    tBgpPeerNgPfxLmtInheritance      TruthValue,
    tBgpPeerNgPfxLmtHoldExcess       Integer32
}

tBgpPeerNgPfxLmtFamily           OBJECT-TYPE
    SYNTAX      TmnxIpFamilyIdentifier
    MAX-ACCESS  not-accessible
    STATUS      current
    DESCRIPTION
        "The value of tBgpPeerNgPfxLmtFamily specifies the address family for
         which prefix-limit is configured."
    ::= { tBgpPeerNgPfxLmtEntry 1 }

tBgpPeerNgPfxLmtLastChanged      OBJECT-TYPE
    SYNTAX      TimeStamp
    MAX-ACCESS  read-only
    STATUS      current
    DESCRIPTION
        "The value tBgpPeerNgPfxLmtLastChanged indicates when an entry in
         tBgpPeerNgPfxLmtTable was last changed."
    ::= { tBgpPeerNgPfxLmtEntry 2 }

tBgpPeerNgPfxLmtRowStatus        OBJECT-TYPE
    SYNTAX      RowStatus
    MAX-ACCESS  read-create
    STATUS      current
    DESCRIPTION
        "The value of tBgpPeerNgPfxLmtRowStatus specifies the row status for
         this BGP instance for the virtual router. It is used to create and
         delete row entries in this table."
    ::= { tBgpPeerNgPfxLmtEntry 3 }

tBgpPeerNgPfxLmtMaxPrefix        OBJECT-TYPE
    SYNTAX      BgpPrefixLimit
    UNITS       "number of routes"
    MAX-ACCESS  read-create
    STATUS      current
    DESCRIPTION
        "The value of tBgpPeerNgPfxLmtMaxPrefix specifies the maximum number of
         routes that can be learned from this peer.

         A value of zero specifies that there is no limit to the number of
         routes learned.

         The tBgpMaxNgPfxLmtThresholdReached notification is sent when the
         number of routes exceeds a percentage of this limit as specified by
         tBgpPeerNgPfxLmtThreshold.

         If the number of routes exceeds this limit, then BGP peering will be
         disabled and the tBgpMaxNgPfxLmt notification will be sent.

         An 'inconsistentValue' error is returned if an attempt is made to set
         this object to its default value. This object can be reset by setting
         the inheritance object tBgpPeerNgPfxLmtInheritance to 'true'."
    DEFVAL      { 0 }
    ::= { tBgpPeerNgPfxLmtEntry 4 }

tBgpPeerNgPfxLmtLogOnly          OBJECT-TYPE
    SYNTAX      TruthValue
    MAX-ACCESS  read-create
    STATUS      current
    DESCRIPTION
        "The value of tBgpPeerNgPfxLmtLogOnly specifies whether BGP peering
         will be disabled when tBgpPeerNgPfxLmtMaxPrefix is exceeded.

         When the value is set to 'true', BGP peering will be enabled.

         When the value is set to 'false', BGP peering will be disabled."
    DEFVAL      { false }
    ::= { tBgpPeerNgPfxLmtEntry 5 }

tBgpPeerNgPfxLmtThreshold        OBJECT-TYPE
    SYNTAX      Unsigned32 (1..100)
    UNITS       "percent"
    MAX-ACCESS  read-create
    STATUS      current
    DESCRIPTION
        "The value of tBgpPeerNgPfxLmtThreshold specifies a percentage of
         tBgpPeerNgPfxLmtMaxPrefix."
    DEFVAL      { 90 }
    ::= { tBgpPeerNgPfxLmtEntry 6 }

tBgpPeerNgPfxLmtIdleTimeOut      OBJECT-TYPE
    SYNTAX      Integer32 (0..1024)
    UNITS       "minutes"
    MAX-ACCESS  read-create
    STATUS      current
    DESCRIPTION
        "The value of tBgpPeerNgPfxLmtIdleTimeOut specifies the idle time in
         minutes that the BGP peering remains disabled before attempting to
         automatically re-establish the connection with this BGP peer after the
         tBgpPeerNgPfxLmtMaxPrefix limit is reached.

         The default value of tBgpPeerNgPfxLmtIdleTimeOut is zero which means,
         no attempt will be made to re-establish the BGP peering with this BGP
         peer after tBgpPeerNgPfxLmtMaxPrefix limit is reached.

         When the value of tBgpPeerNgPfxLmtMaxPrefix is changed, the value of
         tBgpPeerNgPfxLmtIdleTimeOut is reset to its default value.

         The value of tBgpPeerNgPfxLmtIdleTimeOut is inherited from the
         corresponding object value in the tBgpPeerGroupPfxLmtTable, when the
         inheritance object tBgpPeerNgPfxLmtInheritance is set to 'true'. An
         'inconsistentValue' error is returned if an attempt is made to set
         this object to a non-default value when the value of
         tBgpPeerNgPfxLmtMaxPrefix is inherited from group.

         An 'inconsistentValue' error is returned if an attempt is made to set
         this object to a non-default value when the value of
         tBgpPeerNgPfxLmtLogOnly is set to non-default value."
    DEFVAL      { 0 }
    ::= { tBgpPeerNgPfxLmtEntry 7 }

tBgpPeerNgPfxLmtPostImport       OBJECT-TYPE
    SYNTAX      TruthValue
    MAX-ACCESS  read-create
    STATUS      current
    DESCRIPTION
        "The value of tBgpPeerNgPfxLmtPostImport specifies that a route
         rejected by a BGP import policy should not be counted against the
         configured tBgpPeerNgPfxLmtMaxPrefix limit.

         When the value is set to 'true', it specifies that the limit should be
         enforced after import policies."
    DEFVAL      { false }
    ::= { tBgpPeerNgPfxLmtEntry 8 }

tBgpPeerNgPfxLmtInheritance      OBJECT-TYPE
    SYNTAX      TruthValue
    MAX-ACCESS  read-only
    STATUS      current
    DESCRIPTION
        "The value of tBgpPeerNgPfxLmtInheritance specifies if the peer entry
         in this row, should inherit the operational value of an object, or use
         the administratively set value.

         When the value is 'false', then the object's administrative and
         operational value are whatever the DEFVAL or most recently SET value
         is.

         When the value is 'true', then the object's administrative and
         operational value are inherited from the corresponding object in
         tBgpPeerGroupPfxLmtTable."
    DEFVAL      { true }
    ::= { tBgpPeerNgPfxLmtEntry 9 }

tBgpPeerNgPfxLmtHoldExcess       OBJECT-TYPE
    SYNTAX      Integer32 (-1 | 1..100)
    UNITS       "percent"
    MAX-ACCESS  read-create
    STATUS      current
    DESCRIPTION
        "The value of tBgpPeerNgPfxLmtHoldExcess specifies a percentage of
         tBgpPeerNgPfxLmtMaxPrefix.

         When the number of received routes reaches the limit (or a percentage
         of the limit), those  excess routes are retained in the BGP RIB-IN,
         but not installed to the route table/FIB.  Excess routes are not
         automatically installed when room becomes available due to route
         withdrawals  or policy rejections. A clear command must be issued to
         trigger re-evaluation. When the value is set to -1, the received
         routes would be handled by other desired behaviors other than holding
         excess routes"
    DEFVAL      { -1 }
    ::= { tBgpPeerNgPfxLmtEntry 12 }

tBgpPeerLLGRFamilyTblLstCh       OBJECT-TYPE
    SYNTAX      TimeStamp
    MAX-ACCESS  read-only
    STATUS      current
    DESCRIPTION
        "The value of tBgpPeerLLGRFamilyTblLstCh indicates the timestamp when
         an entry in tBgpPeerLLGRFamilyTable was last changed."
    ::= { tBgpPeerObjects 14 }

tBgpPeerLLGRFamilyTable          OBJECT-TYPE
    SYNTAX      SEQUENCE OF TBgpPeerLLGRFamilyEntry
    MAX-ACCESS  not-accessible
    STATUS      current
    DESCRIPTION
        "The tBgpPeerLLGRFamilyTable consists of information about the BGP LLGR
         Family specific parameters. The table entries are indexed by BGP
         instance, Peer Address Peer Address type and LLGR AFI/SAFI."
    ::= { tBgpPeerObjects 15 }

tBgpPeerLLGRFamilyEntry          OBJECT-TYPE
    SYNTAX      TBgpPeerLLGRFamilyEntry
    MAX-ACCESS  not-accessible
    STATUS      current
    DESCRIPTION
        "An entry (conceptual row) in the tBgpPeerLLGRFamilyTable."
    INDEX       {
        tBgpPeerNgInstanceIndex,
        tBgpPeerNgAddressType,
        tBgpPeerNgAddress,
        tBgpPeerLLGRFamily
    }
    ::= { tBgpPeerLLGRFamilyTable 1 }

TBgpPeerLLGRFamilyEntry          ::= SEQUENCE
{
    tBgpPeerLLGRFamily               TmnxIpFamilyIdentifier,
    tBgpPeerLLGRFamilyLstCh          TimeStamp,
    tBgpPeerLLGRFamilyRowStatus      RowStatus,
    tBgpPeerLLGRFamilyAdvStaleTime   Unsigned32,
    tBgpPeerLLGRFamilyOvrideStaleTm  Unsigned32,
    tBgpPeerLLGRFamilyAdvStaleTmRcv  Unsigned32,
    tBgpPeerLLGRFamilyStaleTmNgt     Unsigned32,
    tBgpPeerLLGRFamilyFlagsReceived  OCTET STRING,
    tBgpPeerLLGRFamilyFlagsSupported OCTET STRING
}

tBgpPeerLLGRFamily               OBJECT-TYPE
    SYNTAX      TmnxIpFamilyIdentifier
    MAX-ACCESS  not-accessible
    STATUS      current
    DESCRIPTION
        "The value of tBgpPeerLLGRFamily specifies the particular AFI/SAFI that
         this configuration applies to."
    ::= { tBgpPeerLLGRFamilyEntry 1 }

tBgpPeerLLGRFamilyLstCh          OBJECT-TYPE
    SYNTAX      TimeStamp
    MAX-ACCESS  read-only
    STATUS      current
    DESCRIPTION
        "The value tBgpPeerLLGRFamilyLstCh indicates when an entry in
         tBgpPeerLLGRFamilyTable was last changed."
    ::= { tBgpPeerLLGRFamilyEntry 2 }

tBgpPeerLLGRFamilyRowStatus      OBJECT-TYPE
    SYNTAX      RowStatus
    MAX-ACCESS  read-create
    STATUS      current
    DESCRIPTION
        "RowStatus for the Peer LLGR Family entry."
    ::= { tBgpPeerLLGRFamilyEntry 3 }

tBgpPeerLLGRFamilyAdvStaleTime   OBJECT-TYPE
    SYNTAX      Unsigned32 (0..16777215)
    UNITS       "seconds"
    MAX-ACCESS  read-create
    STATUS      current
    DESCRIPTION
        "The value of tBgpPeerLLGRFamilyAdvStaleTime specifies the time for
         which the route can be used for this AFI/SAFI after the peer is
         disconnected."
    DEFVAL      { 86400 }
    ::= { tBgpPeerLLGRFamilyEntry 4 }

tBgpPeerLLGRFamilyOvrideStaleTm  OBJECT-TYPE
    SYNTAX      Unsigned32 (0..16777216)
    UNITS       "seconds"
    MAX-ACCESS  read-create
    STATUS      current
    DESCRIPTION
        "The value of tBgpPeerLLGRFamilyOvrideStaleTm specifies the stale time
         for this particular AFI/SAFI when the system is in helper mode."
    DEFVAL      { 16777216 }
    ::= { tBgpPeerLLGRFamilyEntry 5 }

tBgpPeerLLGRFamilyAdvStaleTmRcv  OBJECT-TYPE
    SYNTAX      Unsigned32
    MAX-ACCESS  read-only
    STATUS      current
    DESCRIPTION
        "The value of tBgpPeerLLGRFamilyAdvStaleTmRcv indicates the long lived
         stale time received from the peer for this family."
    ::= { tBgpPeerLLGRFamilyEntry 6 }

tBgpPeerLLGRFamilyStaleTmNgt     OBJECT-TYPE
    SYNTAX      Unsigned32
    MAX-ACCESS  read-only
    STATUS      current
    DESCRIPTION
        "The value of tBgpPeerLLGRFamilyStaleTmNgt indicates the long lived
         stale time negotiated with the peer for this family."
    ::= { tBgpPeerLLGRFamilyEntry 7 }

tBgpPeerLLGRFamilyFlagsReceived  OBJECT-TYPE
    SYNTAX      OCTET STRING (SIZE (1))
    MAX-ACCESS  read-only
    STATUS      current
    DESCRIPTION
        "The value of tBgpPeerLLGRFamilyFlagsReceived indicates whether the
         F-bit is negotiated with the peer for this family."
    ::= { tBgpPeerLLGRFamilyEntry 8 }

tBgpPeerLLGRFamilyFlagsSupported OBJECT-TYPE
    SYNTAX      OCTET STRING (SIZE (1))
    MAX-ACCESS  read-only
    STATUS      current
    DESCRIPTION
        "The value of tBgpPeerLLGRFamilyFlagsSupported indicates whether the
         F-bit is negotiated with the peer for this family."
    ::= { tBgpPeerLLGRFamilyEntry 9 }

tBgpPeerNgParamsExtTblLstCh      OBJECT-TYPE
    SYNTAX      TimeStamp
    MAX-ACCESS  read-only
    STATUS      current
    DESCRIPTION
        "The value of tBgpPeerNgParamsExtTblLstCh indicates the timestamp when
         an entry in the tBgpPeerNgParamsExtTable was last changed."
    ::= { tBgpPeerObjects 16 }

tBgpPeerNgParamsExtTable         OBJECT-TYPE
    SYNTAX      SEQUENCE OF TBgpPeerNgParamsExtEntry
    MAX-ACCESS  not-accessible
    STATUS      current
    DESCRIPTION
        "The tBgpPeerNgParamsExtTable consists of information about the
         attributes configured for the BGP instance.

         The table entries are indexed by BGP instance."
    ::= { tBgpPeerObjects 17 }

tBgpPeerNgParamsExtEntry         OBJECT-TYPE
    SYNTAX      TBgpPeerNgParamsExtEntry
    MAX-ACCESS  not-accessible
    STATUS      current
    DESCRIPTION
        "An entry in the tBgpPeerNgParamsTable. An entry is created when an
         entry in tBgpPeerNgEntry is. Each entry maintains the attributes
         configured for BGP peer instance."
    AUGMENTS    { tBgpPeerNgEntry }
    ::= { tBgpPeerNgParamsExtTable 1 }

TBgpPeerNgParamsExtEntry         ::= SEQUENCE
{
    tBgpPeerNgParamsExtInheritanceHi TmnxHigh32,
    tBgpPeerNgParamsExtInheritanceLo TmnxLow32,
    tBgpPeerNgDisableLargeComms      TruthValue,
    tBgpPeerNgLinkAcceptEbgp         TmnxIpFamily,
    tBgpPeerNgLinkSendEbgp           TmnxIpFamily,
    tBgpPeerNgLinkAggPaths           TmnxIpFamily,
    tBgpPeerNgLoopDetectThreshold    Unsigned32,
    tBgpPeerNgSendExportPolicy       TLPolicyNameOrExpOrEmpty,
    tBgpPeerNgEbgpPreference         TmnxBgpPreference,
    tBgpPeerNgIbgpPreference         TmnxBgpPreference,
    tBgpPeerNgEbgpLabelPreference    TmnxBgpPreference,
    tBgpPeerNgIbgpLabelPreference    TmnxBgpPreference,
    tBgpPeerNgEBGPRejWithoutPlcyImpt TruthValue,
    tBgpPeerNgEBGPRejWithoutPlcyExpt TruthValue,
    tBgpPeerNgMultipathEligible      TruthValue,
    tBgpPeerNgRemovePrivateReplace   TruthValue,
    tBgpPeerNgBlockPrefixSID         TruthValue,
    tBgpPeerNgSelLabelIpv4Inst       TruthValue,
    tBgpPeerNgDefOriginate           TmnxIpFamily,
    tBgpPeerNgTcpMss                 Unsigned32,
    tBgpPeerNgEgressEng              TruthValue,
    tBgpPeerNgEgressEngShutdown      TmnxAdminState,
    tBgpPeerNgSegmentRoutingV6       TruthValue,
    tBgpPeerNgSrv6RouteAdvertisement TruthValue,
    tBgpPeerNgSrv6DropRoutes         TruthValue,
    tBgpPeerNgEgrPeerEngLabelUnicast TruthValue,
    tBgpPeerNgEvpnLinkBWAddToRcvdBgp Integer32,
    tBgpPeerNgBfdStrictAdvertise     TruthValue,
    tBgpPeerNgBfdStrictNhReach       TruthValue,
    tBgpPeerNgBfdStrictHoldTime      Unsigned32
}

tBgpPeerNgParamsExtInheritanceHi OBJECT-TYPE
    SYNTAX      TmnxHigh32 (0..4294967295)
    MAX-ACCESS  read-create
    STATUS      current
    DESCRIPTION
        "The value of tBgpPeerNgParamsExtInheritanceHi specifies the upper 32
         bits of inheritance object. The object specifies if the peer entry in
         this row, should inherit the operational value of an object, or use
         the administratively set value.

         This object is a bit-mask, with the following positions:


         When the bit for an object is set to one, then the object's
         administrative and operational value are whatever the DEFVAL or most
         recently SET value is.

         When the bit for an object is set to zero, then the object's
         administrative and operational value are inherited from the
         corresponding object in tBgpPeerGroupTable, or from the corresponding
         object in tBgpInstanceTable.

         By default all of these attributes should be inherited from the
         tBgpPeerGroupTable."
    DEFVAL      { 0 }
    ::= { tBgpPeerNgParamsExtEntry 1 }

tBgpPeerNgParamsExtInheritanceLo OBJECT-TYPE
    SYNTAX      TmnxLow32 (0..4294967295)
    MAX-ACCESS  read-create
    STATUS      current
    DESCRIPTION
        "The value of tBgpPeerNgParamsExtInheritanceLo specifies the lower  32
         bits of the inheritance object. The object specifies if the peer entry
         in this row, should inherit the operational value of an object, or use
         the administratively set value.

         This object is a bit-mask, with the following positions:

         tBgpPeerNgParamsExtInheritanceHi   0x00000001
         tBgpPeerNgParamsExtInheritanceLo   0x00000002
         tBgpPeerNgDisableLargeComms        0x00000004
         tBgpPeerNgLinkAcceptEbgp           0x00000008
         tBgpPeerNgLinkSendEbgp             0x00000010
         tBgpPeerNgLinkAggPaths             0x00000020
         tBgpPeerNgLoopDetectThreshold      0x00000040
         feature (TIMOS_FEATURE_BGP_DEFAULT_ORIGINATE) {
         tBgpPeerNgSendExportPolicy         0x00000080
         }
         feature (TIMOS_FEATURE_BGP_EBGP_IBGP_PREFERENCE) {
         tBgpPeerNgEbgpPreference           0x00000100
         tBgpPeerNgIbgpPreference           0x00000200
         tBgpPeerNgEbgpLabelPreference      0x00000400
         tBgpPeerNgIbgpLabelPreference      0x00000800
         }
         feature (TIMOS_FEATURE_BGP_EBGP_REJECT_WITHOUT_PLCY) {
         tBgpPeerNgEBGPRejWithoutPlcyImpt   0x00001000
         tBgpPeerNgEBGPRejWithoutPlcyExpt   0x00002000
         }
         tBgpPeerNgMultipathEligible        0x00004000
         tBgpPeerNgRemovePrivateReplace     0x00008000
         tBgpPeerNgBlockPrefixSID           0x00010000
         tBgpPeerNgSelLabelIpv4Inst         0x00020000
         tBgpPeerNgDefOriginate             0x00040000
         tBgpPeerNgTcpMss                   0x00080000
         tBgpPeerNgEgressEng                0x00100000

         reserved                           0x00200000

         tBgpPeerNgSegmentRoutingV6         0x00800000
         tBgpPeerNgSrv6RouteAdvertisement   0x01000000
         tBgpPeerNgSrv6DropRoutes           0x02000000

         tBgpPeerNgEgrPeerEngLabelUnicast   0x04000000

         tBgpPeerNgEvpnLinkBWAddToRcvdBgp   0x08000000

         tBgpPeerNgBfdStrictAdvertise       0x10000000
         tBgpPeerNgBfdStrictNhReach         0x20000000

         reserved                           0x40000000


         When the bit for an object is set to one, then the object's
         administrative and operational value are whatever the DEFVAL or most
         recently SET value is.

         When the bit for an object is set to zero, then the object's
         administrative and operational value are inherited from the
         corresponding object in tBgpPeerGroupTable, or from the corresponding
         object in tBgpInstanceTable.

         The bits marked as 'reserved' correspond to attributes that do  not
         have inheritance but the bits are reserved.

         By default all of these attributes should be inherited from the
         tBgpPeerGroupTable."
    DEFVAL      { 0 }
    ::= { tBgpPeerNgParamsExtEntry 2 }

tBgpPeerNgDisableLargeComms      OBJECT-TYPE
    SYNTAX      TruthValue
    MAX-ACCESS  read-create
    STATUS      current
    DESCRIPTION
        "The value of tBgpPeerNgDisableLargeComms enables or disables sending
         of community attribute to the peer for large communities."
    DEFVAL      { false }
    ::= { tBgpPeerNgParamsExtEntry 3 }

tBgpPeerNgLinkAcceptEbgp         OBJECT-TYPE
    SYNTAX      TmnxIpFamily
    MAX-ACCESS  read-create
    STATUS      current
    DESCRIPTION
        "The value of tBgpPeerNgLinkAcceptEbgp specifies the address families
         of the routes received from a single-hop EBGP neighbor, for which a
         Link Bandwidth Extended Community with static AS and bandwidth values
         is allowed."
    DEFVAL      { {} }
    ::= { tBgpPeerNgParamsExtEntry 4 }

tBgpPeerNgLinkSendEbgp           OBJECT-TYPE
    SYNTAX      TmnxIpFamily
    MAX-ACCESS  read-create
    STATUS      current
    DESCRIPTION
        "The value of tBgpPeerNgLinkSendEbgp specifies the address families of
         the routes sent to a single-hop EBGP neighbor, for which a Link
         Bandwidth Extended Community with static AS and bandwidth values is
         allowed."
    DEFVAL      { {} }
    ::= { tBgpPeerNgParamsExtEntry 5 }

tBgpPeerNgLinkAggPaths           OBJECT-TYPE
    SYNTAX      TmnxIpFamily
    MAX-ACCESS  read-create
    STATUS      current
    DESCRIPTION
        "The value of tBgpPeerNgLinkAggPaths specifies the families of the
         routes for which aggregate bandwidth is supported  for a
         re-advertising router."
    DEFVAL      { {} }
    ::= { tBgpPeerNgParamsExtEntry 6 }

tBgpPeerNgLoopDetectThreshold    OBJECT-TYPE
    SYNTAX      Unsigned32 (0..15)
    MAX-ACCESS  read-create
    STATUS      current
    DESCRIPTION
        "The value of tBgpPeerNgLoopDetectThreshold specifies the occurrence of
         the global ASN when exceeded triggers the loop-detect behavior."
    DEFVAL      { 0 }
    ::= { tBgpPeerNgParamsExtEntry 7 }

tBgpPeerNgSendExportPolicy       OBJECT-TYPE
    SYNTAX      TLPolicyNameOrExpOrEmpty
    MAX-ACCESS  read-create
    STATUS      current
    DESCRIPTION
        "The value of tBgpPeerNgSendExportPolicy specifies the send default
         export policy."
    DEFVAL      { "" }
    ::= { tBgpPeerNgParamsExtEntry 8 }

tBgpPeerNgEbgpPreference         OBJECT-TYPE
    SYNTAX      TmnxBgpPreference (0..255)
    MAX-ACCESS  read-create
    STATUS      current
    DESCRIPTION
        "The value of tBgpPeerNgEbgpPreference specifies the route preference
         for ebgp routes."
    DEFVAL      { 0 }
    ::= { tBgpPeerNgParamsExtEntry 9 }

tBgpPeerNgIbgpPreference         OBJECT-TYPE
    SYNTAX      TmnxBgpPreference (0..255)
    MAX-ACCESS  read-create
    STATUS      current
    DESCRIPTION
        "The value of tBgpPeerNgIbgpPreference specifies the route preference
         for ibgp routes."
    DEFVAL      { 0 }
    ::= { tBgpPeerNgParamsExtEntry 10 }

tBgpPeerNgEbgpLabelPreference    OBJECT-TYPE
    SYNTAX      TmnxBgpPreference (0..255)
    MAX-ACCESS  read-create
    STATUS      current
    DESCRIPTION
        "The value of tBgpPeerNgEbgpLabelPreference specifies the route
         preference for label-IPv4 and label-IPv6 ebgp routes."
    DEFVAL      { 0 }
    ::= { tBgpPeerNgParamsExtEntry 11 }

tBgpPeerNgIbgpLabelPreference    OBJECT-TYPE
    SYNTAX      TmnxBgpPreference (0..255)
    MAX-ACCESS  read-create
    STATUS      current
    DESCRIPTION
        "The value of tBgpPeerNgIbgpLabelPreference specifies the route
         preference for label-IPv4 and label-IPv6 ibgp routes."
    DEFVAL      { 0 }
    ::= { tBgpPeerNgParamsExtEntry 12 }

tBgpPeerNgEBGPRejWithoutPlcyImpt OBJECT-TYPE
    SYNTAX      TruthValue
    MAX-ACCESS  read-create
    STATUS      current
    DESCRIPTION
        "The value of tBgpPeerNgEBGPRejWithoutPlcyImpt enables or disables if
         policies can be imported."
    DEFVAL      { false }
    ::= { tBgpPeerNgParamsExtEntry 13 }

tBgpPeerNgEBGPRejWithoutPlcyExpt OBJECT-TYPE
    SYNTAX      TruthValue
    MAX-ACCESS  read-create
    STATUS      current
    DESCRIPTION
        "The value of tBgpPeerNgEBGPRejWithoutPlcyExpt enables or disables if
         policies can be exported."
    DEFVAL      { false }
    ::= { tBgpPeerNgParamsExtEntry 14 }

tBgpPeerNgMultipathEligible      OBJECT-TYPE
    SYNTAX      TruthValue
    MAX-ACCESS  read-create
    STATUS      current
    DESCRIPTION
        "The value of tBgpPeerNgMultipathEligible specifies whether this group
         neighbor is multi-path eligible."
    DEFVAL      { false }
    ::= { tBgpPeerNgParamsExtEntry 15 }

tBgpPeerNgRemovePrivateReplace   OBJECT-TYPE
    SYNTAX      TruthValue
    MAX-ACCESS  read-create
    STATUS      current
    DESCRIPTION
        "The value of tBgpPeerNgRemovePrivateReplace specifies whether BGP will
         replace private AS numbers for this peer."
    DEFVAL      { false }
    ::= { tBgpPeerNgParamsExtEntry 16 }

tBgpPeerNgBlockPrefixSID         OBJECT-TYPE
    SYNTAX      TruthValue
    MAX-ACCESS  read-create
    STATUS      current
    DESCRIPTION
        "The value of tBgpPeerNgBlockPrefixSID enables or disables sending of
         the prefix SID attribute."
    DEFVAL      { false }
    ::= { tBgpPeerNgParamsExtEntry 17 }

tBgpPeerNgSelLabelIpv4Inst       OBJECT-TYPE
    SYNTAX      TruthValue
    MAX-ACCESS  read-create
    STATUS      current
    DESCRIPTION
        "The value of tBgpPeerNgSelLabelIpv4Inst specifies whether to
         enable/disable selective download of label-ipv4 routes"
    DEFVAL      { false }
    ::= { tBgpPeerNgParamsExtEntry 18 }

tBgpPeerNgDefOriginate           OBJECT-TYPE
    SYNTAX      TmnxIpFamily
    MAX-ACCESS  read-create
    STATUS      current
    DESCRIPTION
        "The value of tBgpPeerNgDefOriginate specifies the types of AFI/SAFI
         for which SROS BGP will originate default route independent of the RTM
         default route."
    ::= { tBgpPeerNgParamsExtEntry 19 }

tBgpPeerNgTcpMss                 OBJECT-TYPE
    SYNTAX      Unsigned32 (0 | 384..9746)
    MAX-ACCESS  read-create
    STATUS      current
    DESCRIPTION
        "The value of tBgpPeerNgTcpMss specifies the TCP maximum segment
         size(MSS). When the value of tBgpPeerNgTcpMss is set to 0, the command
         removes the static value and allows the TCP MSS value to be calculated
         based on the IP MTU value."
    DEFVAL      { 0 }
    ::= { tBgpPeerNgParamsExtEntry 20 }

tBgpPeerNgEgressEng              OBJECT-TYPE
    SYNTAX      TruthValue
    MAX-ACCESS  read-create
    STATUS      current
    DESCRIPTION
        "The value of tBgpPeerNgEgressEng specifies whether to enable/disable
         egress peer engineering"
    DEFVAL      { false }
    ::= { tBgpPeerNgParamsExtEntry 21 }

tBgpPeerNgEgressEngShutdown      OBJECT-TYPE
    SYNTAX      TmnxAdminState
    MAX-ACCESS  read-create
    STATUS      current
    DESCRIPTION
        "The value of the object tBgpPeerNgEgressEngShutdown specifies the
         desired administrative state of Egress Engineering for this BGP peer."
    DEFVAL      { outOfService }
    ::= { tBgpPeerNgParamsExtEntry 22 }

tBgpPeerNgSegmentRoutingV6       OBJECT-TYPE
    SYNTAX      TruthValue
    MAX-ACCESS  read-create
    STATUS      current
    DESCRIPTION
        "The value of tBgpPeerNgSegmentRoutingV6 specifies whether or not
         segment routing V6 capabilities are enabled on this peer of BGP.

         When the value is set to 'false' segment routing V6 is disabled and
         any previous configuration of other segment routing parameters  is
         removed."
    DEFVAL      { false }
    ::= { tBgpPeerNgParamsExtEntry 24 }

tBgpPeerNgSrv6RouteAdvertisement OBJECT-TYPE
    SYNTAX      TruthValue
    MAX-ACCESS  read-create
    STATUS      current
    DESCRIPTION
        "The value of tBgpPeerNgSrv6RouteAdvertisement specifies whether or not
         segment routing V6 capabilities  for route advertisement
         are enabled on this peer of BGP."
    DEFVAL      { false }
    ::= { tBgpPeerNgParamsExtEntry 25 }

tBgpPeerNgSrv6DropRoutes         OBJECT-TYPE
    SYNTAX      TruthValue
    MAX-ACCESS  read-create
    STATUS      current
    DESCRIPTION
        "The value of tBgpPeerNgSrv6DropRoutes specifies whether or not to drop
         routes with srv6 tlvs for this peer of BGP."
    DEFVAL      { false }
    ::= { tBgpPeerNgParamsExtEntry 26 }

tBgpPeerNgEgrPeerEngLabelUnicast OBJECT-TYPE
    SYNTAX      TruthValue
    MAX-ACCESS  read-create
    STATUS      current
    DESCRIPTION
        "The value of tBgpPeerNgEgrPeerEngLabelUnicast specifies whether  to
         originate label unicast route on this peer of BGP."
    DEFVAL      { false }
    ::= { tBgpPeerNgParamsExtEntry 27 }

tBgpPeerNgEvpnLinkBWAddToRcvdBgp OBJECT-TYPE
    SYNTAX      Integer32 (-1 | 1..128)
    MAX-ACCESS  read-create
    STATUS      current
    DESCRIPTION
        "The value of tBgpPeerNgEvpnLinkBWAddToRcvdBgp specifies whether a
         weight  is internally added to the received PE-CE BGP routes in the
         VPRN and what  that weight is on this peer of BGP.

         For the purpose of unequal ECMP, if EVPN-IFL and BGP PE-CE routes are
         combined into the same ECMP set and the value is in the range of
         [1..128],  the configured weight is added to all BGP PE-CE routes.
         When the value is  set to -1, ECMP set resulting from combining
         EVPN-IFL and BGP PE-CE route  will fallback to unweighted ECMP"
    DEFVAL      { -1 }
    ::= { tBgpPeerNgParamsExtEntry 28 }

tBgpPeerNgBfdStrictAdvertise     OBJECT-TYPE
    SYNTAX      TruthValue
    MAX-ACCESS  read-create
    STATUS      current
    DESCRIPTION
        "The value of tBgpPeerNgBfdStrictAdvertise specifies whether strict
         Bi-directional Forwarding Detection will be advertised by this router.

         When the value is 'true', strict BFD mode capability is announced by
         this router"
    DEFVAL      { false }
    ::= { tBgpPeerNgParamsExtEntry 29 }

tBgpPeerNgBfdStrictNhReach       OBJECT-TYPE
    SYNTAX      TruthValue
    MAX-ACCESS  read-create
    STATUS      current
    DESCRIPTION
        "The value of tBgpPeerNgBfdStrictNhReach specifies whether strict BFD
         mode will be used for next-hop reachability.

         When the value is 'true', the strict BFD state will be applied to the
         BGP next-hop"
    DEFVAL      { false }
    ::= { tBgpPeerNgParamsExtEntry 30 }

tBgpPeerNgBfdStrictHoldTime      OBJECT-TYPE
    SYNTAX      Unsigned32 (1..65535)
    MAX-ACCESS  read-create
    STATUS      current
    DESCRIPTION
        "The value of tBgpPeerNgBfdStrictHoldTime specifies the BGP session
         hold time when the strict mode BFD session is not successfully
         established.

         When the value is not '0' the BGP session will be bounced after the
         configured time"
    DEFVAL      { 30 }
    ::= { tBgpPeerNgParamsExtEntry 31 }

tBgpPeerNgEpeIngrStatsTable      OBJECT-TYPE
    SYNTAX      SEQUENCE OF TBgpPeerNgEpeIngrStatsEntry
    MAX-ACCESS  not-accessible
    STATUS      current
    DESCRIPTION
        "The tBgpPeerNgEpeIngrStatsTable is operational status information for
         egress engineering."
    ::= { tBgpPeerObjects 18 }

tBgpPeerNgEpeIngrStatsEntry      OBJECT-TYPE
    SYNTAX      TBgpPeerNgEpeIngrStatsEntry
    MAX-ACCESS  not-accessible
    STATUS      current
    DESCRIPTION
        "Defines an entry (conceptual row) in the tBgpPeerNgEpeIngrStatsTable.

         Entries in tBgpPeerNgEpeIngrStatsTable are created by the system when
         tBgpEgressEng is set to 'true' and tBgpEgressEngShutdown is set to
         'inService', and tBgpPeerNgEgressEng is set to 'true' and
         tBgpPeerNgEgressEngShutdown  is set to 'inService'."
    INDEX       {
        tBgpPeerNgInstanceIndex,
        tBgpPeerNgAddressType,
        tBgpPeerNgAddress
    }
    ::= { tBgpPeerNgEpeIngrStatsTable 1 }

TBgpPeerNgEpeIngrStatsEntry      ::= SEQUENCE
{
    tBgpPeerNgNodeSid                Unsigned32,
    tBgpPeerNgNodeSidStatsPktCnt     Counter64,
    tBgpPeerNgNodeSidStatsByteCnt    Counter64,
    tBgpPeerNgAdjSid1Value           Unsigned32,
    tBgpPeerNgAdjSid1StatsPktCnt     Counter64,
    tBgpPeerNgAdjSid1StatsByteCnt    Counter64,
    tBgpPeerNgAdjSid2Value           Unsigned32,
    tBgpPeerNgAdjSid2StatsPktCnt     Counter64,
    tBgpPeerNgAdjSid2StatsByteCnt    Counter64,
    tBgpPeerNgAdjSid3Value           Unsigned32,
    tBgpPeerNgAdjSid3StatsPktCnt     Counter64,
    tBgpPeerNgAdjSid3StatsByteCnt    Counter64,
    tBgpPeerNgAdjSid4Value           Unsigned32,
    tBgpPeerNgAdjSid4StatsPktCnt     Counter64,
    tBgpPeerNgAdjSid4StatsByteCnt    Counter64,
    tBgpPeerNgAdjSid5Value           Unsigned32,
    tBgpPeerNgAdjSid5StatsPktCnt     Counter64,
    tBgpPeerNgAdjSid5StatsByteCnt    Counter64,
    tBgpPeerNgAdjSid6Value           Unsigned32,
    tBgpPeerNgAdjSid6StatsPktCnt     Counter64,
    tBgpPeerNgAdjSid6StatsByteCnt    Counter64,
    tBgpPeerNgAdjSid7Value           Unsigned32,
    tBgpPeerNgAdjSid7StatsPktCnt     Counter64,
    tBgpPeerNgAdjSid7StatsByteCnt    Counter64,
    tBgpPeerNgAdjSid8Value           Unsigned32,
    tBgpPeerNgAdjSid8StatsPktCnt     Counter64,
    tBgpPeerNgAdjSid8StatsByteCnt    Counter64,
    tBgpPeerNgAdjSid9Value           Unsigned32,
    tBgpPeerNgAdjSid9StatsPktCnt     Counter64,
    tBgpPeerNgAdjSid9StatsByteCnt    Counter64,
    tBgpPeerNgAdjSid10Value          Unsigned32,
    tBgpPeerNgAdjSid10StatsPktCnt    Counter64,
    tBgpPeerNgAdjSid10StatsByteCnt   Counter64,
    tBgpPeerNgAdjSid11Value          Unsigned32,
    tBgpPeerNgAdjSid11StatsPktCnt    Counter64,
    tBgpPeerNgAdjSid11StatsByteCnt   Counter64,
    tBgpPeerNgAdjSid12Value          Unsigned32,
    tBgpPeerNgAdjSid12StatsPktCnt    Counter64,
    tBgpPeerNgAdjSid12StatsByteCnt   Counter64,
    tBgpPeerNgAdjSid13Value          Unsigned32,
    tBgpPeerNgAdjSid13StatsPktCnt    Counter64,
    tBgpPeerNgAdjSid13StatsByteCnt   Counter64,
    tBgpPeerNgAdjSid14Value          Unsigned32,
    tBgpPeerNgAdjSid14StatsPktCnt    Counter64,
    tBgpPeerNgAdjSid14StatsByteCnt   Counter64,
    tBgpPeerNgAdjSid15Value          Unsigned32,
    tBgpPeerNgAdjSid15StatsPktCnt    Counter64,
    tBgpPeerNgAdjSid15StatsByteCnt   Counter64,
    tBgpPeerNgAdjSid16Value          Unsigned32,
    tBgpPeerNgAdjSid16StatsPktCnt    Counter64,
    tBgpPeerNgAdjSid16StatsByteCnt   Counter64,
    tBgpPeerNgAdjSid17Value          Unsigned32,
    tBgpPeerNgAdjSid17StatsPktCnt    Counter64,
    tBgpPeerNgAdjSid17StatsByteCnt   Counter64,
    tBgpPeerNgAdjSid18Value          Unsigned32,
    tBgpPeerNgAdjSid18StatsPktCnt    Counter64,
    tBgpPeerNgAdjSid18StatsByteCnt   Counter64,
    tBgpPeerNgAdjSid19Value          Unsigned32,
    tBgpPeerNgAdjSid19StatsPktCnt    Counter64,
    tBgpPeerNgAdjSid19StatsByteCnt   Counter64,
    tBgpPeerNgAdjSid20Value          Unsigned32,
    tBgpPeerNgAdjSid20StatsPktCnt    Counter64,
    tBgpPeerNgAdjSid20StatsByteCnt   Counter64,
    tBgpPeerNgAdjSid21Value          Unsigned32,
    tBgpPeerNgAdjSid21StatsPktCnt    Counter64,
    tBgpPeerNgAdjSid21StatsByteCnt   Counter64,
    tBgpPeerNgAdjSid22Value          Unsigned32,
    tBgpPeerNgAdjSid22StatsPktCnt    Counter64,
    tBgpPeerNgAdjSid22StatsByteCnt   Counter64,
    tBgpPeerNgAdjSid23Value          Unsigned32,
    tBgpPeerNgAdjSid23StatsPktCnt    Counter64,
    tBgpPeerNgAdjSid23StatsByteCnt   Counter64,
    tBgpPeerNgAdjSid24Value          Unsigned32,
    tBgpPeerNgAdjSid24StatsPktCnt    Counter64,
    tBgpPeerNgAdjSid24StatsByteCnt   Counter64,
    tBgpPeerNgAdjSid25Value          Unsigned32,
    tBgpPeerNgAdjSid25StatsPktCnt    Counter64,
    tBgpPeerNgAdjSid25StatsByteCnt   Counter64,
    tBgpPeerNgAdjSid26Value          Unsigned32,
    tBgpPeerNgAdjSid26StatsPktCnt    Counter64,
    tBgpPeerNgAdjSid26StatsByteCnt   Counter64,
    tBgpPeerNgAdjSid27Value          Unsigned32,
    tBgpPeerNgAdjSid27StatsPktCnt    Counter64,
    tBgpPeerNgAdjSid27StatsByteCnt   Counter64,
    tBgpPeerNgAdjSid28Value          Unsigned32,
    tBgpPeerNgAdjSid28StatsPktCnt    Counter64,
    tBgpPeerNgAdjSid28StatsByteCnt   Counter64,
    tBgpPeerNgAdjSid29Value          Unsigned32,
    tBgpPeerNgAdjSid29StatsPktCnt    Counter64,
    tBgpPeerNgAdjSid29StatsByteCnt   Counter64,
    tBgpPeerNgAdjSid30Value          Unsigned32,
    tBgpPeerNgAdjSid30StatsPktCnt    Counter64,
    tBgpPeerNgAdjSid30StatsByteCnt   Counter64,
    tBgpPeerNgAdjSid31Value          Unsigned32,
    tBgpPeerNgAdjSid31StatsPktCnt    Counter64,
    tBgpPeerNgAdjSid31StatsByteCnt   Counter64,
    tBgpPeerNgAdjSid32Value          Unsigned32,
    tBgpPeerNgAdjSid32StatsPktCnt    Counter64,
    tBgpPeerNgAdjSid32StatsByteCnt   Counter64
}

tBgpPeerNgNodeSid                OBJECT-TYPE
    SYNTAX      Unsigned32
    MAX-ACCESS  read-only
    STATUS      current
    DESCRIPTION
        "The value of tBgpPeerNgNodeSid specifies the node sid value."
    ::= { tBgpPeerNgEpeIngrStatsEntry 1 }

tBgpPeerNgNodeSidStatsPktCnt     OBJECT-TYPE
    SYNTAX      Counter64
    MAX-ACCESS  read-only
    STATUS      current
    DESCRIPTION
        "The value of tBgpPeerNgNodeSidStatsPktCnt indicates the number of packets
         for  this peer."
    ::= { tBgpPeerNgEpeIngrStatsEntry 2 }

tBgpPeerNgNodeSidStatsByteCnt    OBJECT-TYPE
    SYNTAX      Counter64
    MAX-ACCESS  read-only
    STATUS      current
    DESCRIPTION
        "The value of tBgpPeerNgNodeSidStatsByteCnt indicates the number of
         bytes for this peer."
    ::= { tBgpPeerNgEpeIngrStatsEntry 3 }

tBgpPeerNgAdjSid1Value           OBJECT-TYPE
    SYNTAX      Unsigned32
    MAX-ACCESS  read-only
    STATUS      current
    DESCRIPTION
        "The value of tBgpPeerNgAdjSid1Value specifies the adjacent sid value."
    ::= { tBgpPeerNgEpeIngrStatsEntry 4 }

tBgpPeerNgAdjSid1StatsPktCnt     OBJECT-TYPE
    SYNTAX      Counter64
    MAX-ACCESS  read-only
    STATUS      current
    DESCRIPTION
        "The value of tBgpPeerNgAdjSid1StatsPktCnt indicates the number of
         packets for this peer."
    ::= { tBgpPeerNgEpeIngrStatsEntry 5 }

tBgpPeerNgAdjSid1StatsByteCnt    OBJECT-TYPE
    SYNTAX      Counter64
    MAX-ACCESS  read-only
    STATUS      current
    DESCRIPTION
        "The value of tBgpPeerNgAdjSid1StatsByteCnt indicates the number of
         bytes for this peer."
    ::= { tBgpPeerNgEpeIngrStatsEntry 6 }

tBgpPeerNgAdjSid2Value           OBJECT-TYPE
    SYNTAX      Unsigned32
    MAX-ACCESS  read-only
    STATUS      current
    DESCRIPTION
        "The value of tBgpPeerNgAdjSid2Value specifies the adjacent sid value."
    ::= { tBgpPeerNgEpeIngrStatsEntry 7 }

tBgpPeerNgAdjSid2StatsPktCnt     OBJECT-TYPE
    SYNTAX      Counter64
    MAX-ACCESS  read-only
    STATUS      current
    DESCRIPTION
        "The value of tBgpPeerNgAdjSid2StatsPktCnt indicates the number of
         packets for this peer."
    ::= { tBgpPeerNgEpeIngrStatsEntry 8 }

tBgpPeerNgAdjSid2StatsByteCnt    OBJECT-TYPE
    SYNTAX      Counter64
    MAX-ACCESS  read-only
    STATUS      current
    DESCRIPTION
        "The value of tBgpPeerNgAdjSid2StatsByteCnt indicates the number of
         bytes for this peer."
    ::= { tBgpPeerNgEpeIngrStatsEntry 9 }

tBgpPeerNgAdjSid3Value           OBJECT-TYPE
    SYNTAX      Unsigned32
    MAX-ACCESS  read-only
    STATUS      current
    DESCRIPTION
        "The value of tBgpPeerNgAdjSid3Value specifies the adjacent sid value."
    ::= { tBgpPeerNgEpeIngrStatsEntry 10 }

tBgpPeerNgAdjSid3StatsPktCnt     OBJECT-TYPE
    SYNTAX      Counter64
    MAX-ACCESS  read-only
    STATUS      current
    DESCRIPTION
        "The value of tBgpPeerNgAdjSid3StatsPktCnt indicates the number of
         packets for this peer."
    ::= { tBgpPeerNgEpeIngrStatsEntry 11 }

tBgpPeerNgAdjSid3StatsByteCnt    OBJECT-TYPE
    SYNTAX      Counter64
    MAX-ACCESS  read-only
    STATUS      current
    DESCRIPTION
        "The value of tBgpPeerNgAdjSid3StatsByteCnt indicates the number of
         bytes for this peer."
    ::= { tBgpPeerNgEpeIngrStatsEntry 12 }

tBgpPeerNgAdjSid4Value           OBJECT-TYPE
    SYNTAX      Unsigned32
    MAX-ACCESS  read-only
    STATUS      current
    DESCRIPTION
        "The value of tBgpPeerNgAdjSid4Value specifies the adjacent sid value."
    ::= { tBgpPeerNgEpeIngrStatsEntry 13 }

tBgpPeerNgAdjSid4StatsPktCnt     OBJECT-TYPE
    SYNTAX      Counter64
    MAX-ACCESS  read-only
    STATUS      current
    DESCRIPTION
        "The value of tBgpPeerNgAdjSid4StatsPktCnt indicates the number of
         packets for this peer."
    ::= { tBgpPeerNgEpeIngrStatsEntry 14 }

tBgpPeerNgAdjSid4StatsByteCnt    OBJECT-TYPE
    SYNTAX      Counter64
    MAX-ACCESS  read-only
    STATUS      current
    DESCRIPTION
        "The value of tBgpPeerNgAdjSid4StatsByteCnt indicates the number of
         bytes for this peer."
    ::= { tBgpPeerNgEpeIngrStatsEntry 15 }

tBgpPeerNgAdjSid5Value           OBJECT-TYPE
    SYNTAX      Unsigned32
    MAX-ACCESS  read-only
    STATUS      current
    DESCRIPTION
        "The value of tBgpPeerNgAdjSid5Value specifies the adjacent sid value."
    ::= { tBgpPeerNgEpeIngrStatsEntry 16 }

tBgpPeerNgAdjSid5StatsPktCnt     OBJECT-TYPE
    SYNTAX      Counter64
    MAX-ACCESS  read-only
    STATUS      current
    DESCRIPTION
        "The value of tBgpPeerNgAdjSid5StatsPktCnt indicates the number of
         packets for this peer."
    ::= { tBgpPeerNgEpeIngrStatsEntry 17 }

tBgpPeerNgAdjSid5StatsByteCnt    OBJECT-TYPE
    SYNTAX      Counter64
    MAX-ACCESS  read-only
    STATUS      current
    DESCRIPTION
        "The value of tBgpPeerNgAdjSid5StatsByteCnt indicates the number of
         bytes for this peer."
    ::= { tBgpPeerNgEpeIngrStatsEntry 18 }

tBgpPeerNgAdjSid6Value           OBJECT-TYPE
    SYNTAX      Unsigned32
    MAX-ACCESS  read-only
    STATUS      current
    DESCRIPTION
        "The value of tBgpPeerNgAdjSid6Value specifies the adjacent sid value."
    ::= { tBgpPeerNgEpeIngrStatsEntry 19 }

tBgpPeerNgAdjSid6StatsPktCnt     OBJECT-TYPE
    SYNTAX      Counter64
    MAX-ACCESS  read-only
    STATUS      current
    DESCRIPTION
        "The value of tBgpPeerNgAdjSid6StatsPktCnt indicates the number of
         packets for this peer."
    ::= { tBgpPeerNgEpeIngrStatsEntry 20 }

tBgpPeerNgAdjSid6StatsByteCnt    OBJECT-TYPE
    SYNTAX      Counter64
    MAX-ACCESS  read-only
    STATUS      current
    DESCRIPTION
        "The value of tBgpPeerNgAdjSid6StatsByteCnt indicates the number of
         bytes for this peer."
    ::= { tBgpPeerNgEpeIngrStatsEntry 21 }

tBgpPeerNgAdjSid7Value           OBJECT-TYPE
    SYNTAX      Unsigned32
    MAX-ACCESS  read-only
    STATUS      current
    DESCRIPTION
        "The value of tBgpPeerNgAdjSid7Value specifies the adjacent sid value."
    ::= { tBgpPeerNgEpeIngrStatsEntry 22 }

tBgpPeerNgAdjSid7StatsPktCnt     OBJECT-TYPE
    SYNTAX      Counter64
    MAX-ACCESS  read-only
    STATUS      current
    DESCRIPTION
        "The value of tBgpPeerNgAdjSid7StatsPktCnt indicates the number of
         packets for this peer."
    ::= { tBgpPeerNgEpeIngrStatsEntry 23 }

tBgpPeerNgAdjSid7StatsByteCnt    OBJECT-TYPE
    SYNTAX      Counter64
    MAX-ACCESS  read-only
    STATUS      current
    DESCRIPTION
        "The value of tBgpPeerNgAdjSid7StatsByteCnt indicates the number of
         bytes for this peer."
    ::= { tBgpPeerNgEpeIngrStatsEntry 24 }

tBgpPeerNgAdjSid8Value           OBJECT-TYPE
    SYNTAX      Unsigned32
    MAX-ACCESS  read-only
    STATUS      current
    DESCRIPTION
        "The value of tBgpPeerNgAdjSid8Value specifies the adjacent sid value."
    ::= { tBgpPeerNgEpeIngrStatsEntry 25 }

tBgpPeerNgAdjSid8StatsPktCnt     OBJECT-TYPE
    SYNTAX      Counter64
    MAX-ACCESS  read-only
    STATUS      current
    DESCRIPTION
        "The value of tBgpPeerNgAdjSid8StatsPktCnt indicates the number of
         packets for this peer."
    ::= { tBgpPeerNgEpeIngrStatsEntry 26 }

tBgpPeerNgAdjSid8StatsByteCnt    OBJECT-TYPE
    SYNTAX      Counter64
    MAX-ACCESS  read-only
    STATUS      current
    DESCRIPTION
        "The value of tBgpPeerNgAdjSid8StatsByteCnt indicates the number of
         bytes for this peer."
    ::= { tBgpPeerNgEpeIngrStatsEntry 27 }

tBgpPeerNgAdjSid9Value           OBJECT-TYPE
    SYNTAX      Unsigned32
    MAX-ACCESS  read-only
    STATUS      current
    DESCRIPTION
        "The value of tBgpPeerNgAdjSid9Value specifies the adjacent sid value."
    ::= { tBgpPeerNgEpeIngrStatsEntry 28 }

tBgpPeerNgAdjSid9StatsPktCnt     OBJECT-TYPE
    SYNTAX      Counter64
    MAX-ACCESS  read-only
    STATUS      current
    DESCRIPTION
        "The value of tBgpPeerNgAdjSid9StatsPktCnt indicates the number of
         packets for this peer."
    ::= { tBgpPeerNgEpeIngrStatsEntry 29 }

tBgpPeerNgAdjSid9StatsByteCnt    OBJECT-TYPE
    SYNTAX      Counter64
    MAX-ACCESS  read-only
    STATUS      current
    DESCRIPTION
        "The value of tBgpPeerNgAdjSid9StatsByteCnt indicates the number of
         bytes for this peer."
    ::= { tBgpPeerNgEpeIngrStatsEntry 30 }

tBgpPeerNgAdjSid10Value          OBJECT-TYPE
    SYNTAX      Unsigned32
    MAX-ACCESS  read-only
    STATUS      current
    DESCRIPTION
        "The value of tBgpPeerNgAdjSid10Value specifies the adjacent sid value."
    ::= { tBgpPeerNgEpeIngrStatsEntry 31 }

tBgpPeerNgAdjSid10StatsPktCnt    OBJECT-TYPE
    SYNTAX      Counter64
    MAX-ACCESS  read-only
    STATUS      current
    DESCRIPTION
        "The value of tBgpPeerNgAdjSid10StatsPktCnt indicates the number of
         packets for this peer."
    ::= { tBgpPeerNgEpeIngrStatsEntry 32 }

tBgpPeerNgAdjSid10StatsByteCnt   OBJECT-TYPE
    SYNTAX      Counter64
    MAX-ACCESS  read-only
    STATUS      current
    DESCRIPTION
        "The value of tBgpPeerNgAdjSid10StatsByteCnt indicates the number of
         bytes for this peer."
    ::= { tBgpPeerNgEpeIngrStatsEntry 33 }

tBgpPeerNgAdjSid11Value          OBJECT-TYPE
    SYNTAX      Unsigned32
    MAX-ACCESS  read-only
    STATUS      current
    DESCRIPTION
        "The value of tBgpPeerNgAdjSid11Value specifies the adjacent sid value."
    ::= { tBgpPeerNgEpeIngrStatsEntry 34 }

tBgpPeerNgAdjSid11StatsPktCnt    OBJECT-TYPE
    SYNTAX      Counter64
    MAX-ACCESS  read-only
    STATUS      current
    DESCRIPTION
        "The value of tBgpPeerNgAdjSid11StatsPktCnt indicates the number of
         packets for this peer."
    ::= { tBgpPeerNgEpeIngrStatsEntry 35 }

tBgpPeerNgAdjSid11StatsByteCnt   OBJECT-TYPE
    SYNTAX      Counter64
    MAX-ACCESS  read-only
    STATUS      current
    DESCRIPTION
        "The value of tBgpPeerNgAdjSid11StatsByteCnt indicates the number of
         bytes for this peer."
    ::= { tBgpPeerNgEpeIngrStatsEntry 36 }

tBgpPeerNgAdjSid12Value          OBJECT-TYPE
    SYNTAX      Unsigned32
    MAX-ACCESS  read-only
    STATUS      current
    DESCRIPTION
        "The value of tBgpPeerNgAdjSid12Value specifies the adjacent sid value."
    ::= { tBgpPeerNgEpeIngrStatsEntry 37 }

tBgpPeerNgAdjSid12StatsPktCnt    OBJECT-TYPE
    SYNTAX      Counter64
    MAX-ACCESS  read-only
    STATUS      current
    DESCRIPTION
        "The value of tBgpPeerNgAdjSid12StatsPktCnt indicates the number of
         packets for this peer."
    ::= { tBgpPeerNgEpeIngrStatsEntry 38 }

tBgpPeerNgAdjSid12StatsByteCnt   OBJECT-TYPE
    SYNTAX      Counter64
    MAX-ACCESS  read-only
    STATUS      current
    DESCRIPTION
        "The value of tBgpPeerNgAdjSid12StatsByteCnt indicates the number of
         bytes for this peer."
    ::= { tBgpPeerNgEpeIngrStatsEntry 39 }

tBgpPeerNgAdjSid13Value          OBJECT-TYPE
    SYNTAX      Unsigned32
    MAX-ACCESS  read-only
    STATUS      current
    DESCRIPTION
        "The value of tBgpPeerNgAdjSid13Value specifies the adjacent sid value."
    ::= { tBgpPeerNgEpeIngrStatsEntry 40 }

tBgpPeerNgAdjSid13StatsPktCnt    OBJECT-TYPE
    SYNTAX      Counter64
    MAX-ACCESS  read-only
    STATUS      current
    DESCRIPTION
        "The value of tBgpPeerNgAdjSid13StatsPktCnt indicates the number of
         packets for this peer."
    ::= { tBgpPeerNgEpeIngrStatsEntry 41 }

tBgpPeerNgAdjSid13StatsByteCnt   OBJECT-TYPE
    SYNTAX      Counter64
    MAX-ACCESS  read-only
    STATUS      current
    DESCRIPTION
        "The value of tBgpPeerNgAdjSid13StatsByteCnt indicates the number of
         bytes for this peer."
    ::= { tBgpPeerNgEpeIngrStatsEntry 42 }

tBgpPeerNgAdjSid14Value          OBJECT-TYPE
    SYNTAX      Unsigned32
    MAX-ACCESS  read-only
    STATUS      current
    DESCRIPTION
        "The value of tBgpPeerNgAdjSid14Value specifies the adjacent sid value."
    ::= { tBgpPeerNgEpeIngrStatsEntry 43 }

tBgpPeerNgAdjSid14StatsPktCnt    OBJECT-TYPE
    SYNTAX      Counter64
    MAX-ACCESS  read-only
    STATUS      current
    DESCRIPTION
        "The value of tBgpPeerNgAdjSid14StatsPktCnt indicates the number of
         packets for this peer."
    ::= { tBgpPeerNgEpeIngrStatsEntry 44 }

tBgpPeerNgAdjSid14StatsByteCnt   OBJECT-TYPE
    SYNTAX      Counter64
    MAX-ACCESS  read-only
    STATUS      current
    DESCRIPTION
        "The value of tBgpPeerNgAdjSid14StatsByteCnt indicates the number of
         bytes for this peer."
    ::= { tBgpPeerNgEpeIngrStatsEntry 45 }

tBgpPeerNgAdjSid15Value          OBJECT-TYPE
    SYNTAX      Unsigned32
    MAX-ACCESS  read-only
    STATUS      current
    DESCRIPTION
        "The value of tBgpPeerNgAdjSid15Value specifies the adjacent sid value."
    ::= { tBgpPeerNgEpeIngrStatsEntry 46 }

tBgpPeerNgAdjSid15StatsPktCnt    OBJECT-TYPE
    SYNTAX      Counter64
    MAX-ACCESS  read-only
    STATUS      current
    DESCRIPTION
        "The value of tBgpPeerNgAdjSid15StatsPktCnt indicates the number of
         packets for this peer."
    ::= { tBgpPeerNgEpeIngrStatsEntry 47 }

tBgpPeerNgAdjSid15StatsByteCnt   OBJECT-TYPE
    SYNTAX      Counter64
    MAX-ACCESS  read-only
    STATUS      current
    DESCRIPTION
        "The value of tBgpPeerNgAdjSid15StatsByteCnt indicates the number of
         bytes for this peer."
    ::= { tBgpPeerNgEpeIngrStatsEntry 48 }

tBgpPeerNgAdjSid16Value          OBJECT-TYPE
    SYNTAX      Unsigned32
    MAX-ACCESS  read-only
    STATUS      current
    DESCRIPTION
        "The value of tBgpPeerNgAdjSid16Value specifies the adjacent sid value."
    ::= { tBgpPeerNgEpeIngrStatsEntry 49 }

tBgpPeerNgAdjSid16StatsPktCnt    OBJECT-TYPE
    SYNTAX      Counter64
    MAX-ACCESS  read-only
    STATUS      current
    DESCRIPTION
        "The value of tBgpPeerNgAdjSid16StatsPktCnt indicates the number of
         packets for this peer."
    ::= { tBgpPeerNgEpeIngrStatsEntry 50 }

tBgpPeerNgAdjSid16StatsByteCnt   OBJECT-TYPE
    SYNTAX      Counter64
    MAX-ACCESS  read-only
    STATUS      current
    DESCRIPTION
        "The value of tBgpPeerNgAdjSid16StatsByteCnt indicates the number of
         bytes for this peer."
    ::= { tBgpPeerNgEpeIngrStatsEntry 51 }

tBgpPeerNgAdjSid17Value          OBJECT-TYPE
    SYNTAX      Unsigned32
    MAX-ACCESS  read-only
    STATUS      current
    DESCRIPTION
        "The value of tBgpPeerNgAdjSid17Value specifies the adjacent sid value."
    ::= { tBgpPeerNgEpeIngrStatsEntry 52 }

tBgpPeerNgAdjSid17StatsPktCnt    OBJECT-TYPE
    SYNTAX      Counter64
    MAX-ACCESS  read-only
    STATUS      current
    DESCRIPTION
        "The value of tBgpPeerNgAdjSid17StatsPktCnt indicates the number of
         packets for this peer."
    ::= { tBgpPeerNgEpeIngrStatsEntry 53 }

tBgpPeerNgAdjSid17StatsByteCnt   OBJECT-TYPE
    SYNTAX      Counter64
    MAX-ACCESS  read-only
    STATUS      current
    DESCRIPTION
        "The value of tBgpPeerNgAdjSid17StatsByteCnt indicates the number of
         bytes for this peer."
    ::= { tBgpPeerNgEpeIngrStatsEntry 54 }

tBgpPeerNgAdjSid18Value          OBJECT-TYPE
    SYNTAX      Unsigned32
    MAX-ACCESS  read-only
    STATUS      current
    DESCRIPTION
        "The value of tBgpPeerNgAdjSid18Value specifies the adjacent sid value."
    ::= { tBgpPeerNgEpeIngrStatsEntry 55 }

tBgpPeerNgAdjSid18StatsPktCnt    OBJECT-TYPE
    SYNTAX      Counter64
    MAX-ACCESS  read-only
    STATUS      current
    DESCRIPTION
        "The value of tBgpPeerNgAdjSid18StatsPktCnt indicates the number of
         packets for this peer."
    ::= { tBgpPeerNgEpeIngrStatsEntry 56 }

tBgpPeerNgAdjSid18StatsByteCnt   OBJECT-TYPE
    SYNTAX      Counter64
    MAX-ACCESS  read-only
    STATUS      current
    DESCRIPTION
        "The value of tBgpPeerNgAdjSid18StatsByteCnt indicates the number of
         bytes for this peer."
    ::= { tBgpPeerNgEpeIngrStatsEntry 57 }

tBgpPeerNgAdjSid19Value          OBJECT-TYPE
    SYNTAX      Unsigned32
    MAX-ACCESS  read-only
    STATUS      current
    DESCRIPTION
        "The value of tBgpPeerNgAdjSid19Value specifies the adjacent sid value."
    ::= { tBgpPeerNgEpeIngrStatsEntry 58 }

tBgpPeerNgAdjSid19StatsPktCnt    OBJECT-TYPE
    SYNTAX      Counter64
    MAX-ACCESS  read-only
    STATUS      current
    DESCRIPTION
        "The value of tBgpPeerNgAdjSid19StatsPktCnt indicates the number of
         packets for this peer."
    ::= { tBgpPeerNgEpeIngrStatsEntry 59 }

tBgpPeerNgAdjSid19StatsByteCnt   OBJECT-TYPE
    SYNTAX      Counter64
    MAX-ACCESS  read-only
    STATUS      current
    DESCRIPTION
        "The value of tBgpPeerNgAdjSid19StatsByteCnt indicates the number of
         bytes for this peer."
    ::= { tBgpPeerNgEpeIngrStatsEntry 60 }

tBgpPeerNgAdjSid20Value          OBJECT-TYPE
    SYNTAX      Unsigned32
    MAX-ACCESS  read-only
    STATUS      current
    DESCRIPTION
        "The value of tBgpPeerNgAdjSid20Value specifies the adjacent sid value."
    ::= { tBgpPeerNgEpeIngrStatsEntry 61 }

tBgpPeerNgAdjSid20StatsPktCnt    OBJECT-TYPE
    SYNTAX      Counter64
    MAX-ACCESS  read-only
    STATUS      current
    DESCRIPTION
        "The value of tBgpPeerNgAdjSid20StatsPktCnt indicates the number of
         packets for this peer."
    ::= { tBgpPeerNgEpeIngrStatsEntry 62 }

tBgpPeerNgAdjSid20StatsByteCnt   OBJECT-TYPE
    SYNTAX      Counter64
    MAX-ACCESS  read-only
    STATUS      current
    DESCRIPTION
        "The value of tBgpPeerNgAdjSid20StatsByteCnt indicates the number of
         bytes for this peer."
    ::= { tBgpPeerNgEpeIngrStatsEntry 63 }

tBgpPeerNgAdjSid21Value          OBJECT-TYPE
    SYNTAX      Unsigned32
    MAX-ACCESS  read-only
    STATUS      current
    DESCRIPTION
        "The value of tBgpPeerNgAdjSid21Value specifies the adjacent sid value."
    ::= { tBgpPeerNgEpeIngrStatsEntry 64 }

tBgpPeerNgAdjSid21StatsPktCnt    OBJECT-TYPE
    SYNTAX      Counter64
    MAX-ACCESS  read-only
    STATUS      current
    DESCRIPTION
        "The value of tBgpPeerNgAdjSid21StatsPktCnt indicates the number of
         packets for this peer."
    ::= { tBgpPeerNgEpeIngrStatsEntry 65 }

tBgpPeerNgAdjSid21StatsByteCnt   OBJECT-TYPE
    SYNTAX      Counter64
    MAX-ACCESS  read-only
    STATUS      current
    DESCRIPTION
        "The value of tBgpPeerNgAdjSid21StatsByteCnt indicates the number of
         bytes for this peer."
    ::= { tBgpPeerNgEpeIngrStatsEntry 66 }

tBgpPeerNgAdjSid22Value          OBJECT-TYPE
    SYNTAX      Unsigned32
    MAX-ACCESS  read-only
    STATUS      current
    DESCRIPTION
        "The value of tBgpPeerNgAdjSid22Value specifies the adjacent sid value."
    ::= { tBgpPeerNgEpeIngrStatsEntry 67 }

tBgpPeerNgAdjSid22StatsPktCnt    OBJECT-TYPE
    SYNTAX      Counter64
    MAX-ACCESS  read-only
    STATUS      current
    DESCRIPTION
        "The value of tBgpPeerNgAdjSid22StatsPktCnt indicates the number of
         packets for this peer."
    ::= { tBgpPeerNgEpeIngrStatsEntry 68 }

tBgpPeerNgAdjSid22StatsByteCnt   OBJECT-TYPE
    SYNTAX      Counter64
    MAX-ACCESS  read-only
    STATUS      current
    DESCRIPTION
        "The value of tBgpPeerNgAdjSid22StatsByteCnt indicates the number of
         bytes for this peer."
    ::= { tBgpPeerNgEpeIngrStatsEntry 69 }

tBgpPeerNgAdjSid23Value          OBJECT-TYPE
    SYNTAX      Unsigned32
    MAX-ACCESS  read-only
    STATUS      current
    DESCRIPTION
        "The value of tBgpPeerNgAdjSid23Value specifies the adjacent sid value."
    ::= { tBgpPeerNgEpeIngrStatsEntry 70 }

tBgpPeerNgAdjSid23StatsPktCnt    OBJECT-TYPE
    SYNTAX      Counter64
    MAX-ACCESS  read-only
    STATUS      current
    DESCRIPTION
        "The value of tBgpPeerNgAdjSid23StatsPktCnt indicates the number of
         packets for this peer."
    ::= { tBgpPeerNgEpeIngrStatsEntry 71 }

tBgpPeerNgAdjSid23StatsByteCnt   OBJECT-TYPE
    SYNTAX      Counter64
    MAX-ACCESS  read-only
    STATUS      current
    DESCRIPTION
        "The value of tBgpPeerNgAdjSid23StatsByteCnt indicates the number of
         bytes for this peer."
    ::= { tBgpPeerNgEpeIngrStatsEntry 72 }

tBgpPeerNgAdjSid24Value          OBJECT-TYPE
    SYNTAX      Unsigned32
    MAX-ACCESS  read-only
    STATUS      current
    DESCRIPTION
        "The value of tBgpPeerNgAdjSid24Value specifies the adjacent sid value."
    ::= { tBgpPeerNgEpeIngrStatsEntry 73 }

tBgpPeerNgAdjSid24StatsPktCnt    OBJECT-TYPE
    SYNTAX      Counter64
    MAX-ACCESS  read-only
    STATUS      current
    DESCRIPTION
        "The value of tBgpPeerNgAdjSid24StatsPktCnt indicates the number of
         packets for this peer."
    ::= { tBgpPeerNgEpeIngrStatsEntry 74 }

tBgpPeerNgAdjSid24StatsByteCnt   OBJECT-TYPE
    SYNTAX      Counter64
    MAX-ACCESS  read-only
    STATUS      current
    DESCRIPTION
        "The value of tBgpPeerNgAdjSid24StatsByteCnt indicates the number of
         bytes for this peer."
    ::= { tBgpPeerNgEpeIngrStatsEntry 75 }

tBgpPeerNgAdjSid25Value          OBJECT-TYPE
    SYNTAX      Unsigned32
    MAX-ACCESS  read-only
    STATUS      current
    DESCRIPTION
        "The value of tBgpPeerNgAdjSid25Value specifies the adjacent sid value."
    ::= { tBgpPeerNgEpeIngrStatsEntry 76 }

tBgpPeerNgAdjSid25StatsPktCnt    OBJECT-TYPE
    SYNTAX      Counter64
    MAX-ACCESS  read-only
    STATUS      current
    DESCRIPTION
        "The value of tBgpPeerNgAdjSid25StatsPktCnt indicates the number of
         packets for this peer."
    ::= { tBgpPeerNgEpeIngrStatsEntry 77 }

tBgpPeerNgAdjSid25StatsByteCnt   OBJECT-TYPE
    SYNTAX      Counter64
    MAX-ACCESS  read-only
    STATUS      current
    DESCRIPTION
        "The value of tBgpPeerNgAdjSid25StatsByteCnt indicates the number of
         bytes for this peer."
    ::= { tBgpPeerNgEpeIngrStatsEntry 78 }

tBgpPeerNgAdjSid26Value          OBJECT-TYPE
    SYNTAX      Unsigned32
    MAX-ACCESS  read-only
    STATUS      current
    DESCRIPTION
        "The value of tBgpPeerNgAdjSid26Value specifies the adjacent sid value."
    ::= { tBgpPeerNgEpeIngrStatsEntry 79 }

tBgpPeerNgAdjSid26StatsPktCnt    OBJECT-TYPE
    SYNTAX      Counter64
    MAX-ACCESS  read-only
    STATUS      current
    DESCRIPTION
        "The value of tBgpPeerNgAdjSid26StatsPktCnt indicates the number of
         packets for this peer."
    ::= { tBgpPeerNgEpeIngrStatsEntry 80 }

tBgpPeerNgAdjSid26StatsByteCnt   OBJECT-TYPE
    SYNTAX      Counter64
    MAX-ACCESS  read-only
    STATUS      current
    DESCRIPTION
        "The value of tBgpPeerNgAdjSid26StatsByteCnt indicates the number of
         bytes for this peer."
    ::= { tBgpPeerNgEpeIngrStatsEntry 81 }

tBgpPeerNgAdjSid27Value          OBJECT-TYPE
    SYNTAX      Unsigned32
    MAX-ACCESS  read-only
    STATUS      current
    DESCRIPTION
        "The value of tBgpPeerNgAdjSid27Value specifies the adjacent sid value."
    ::= { tBgpPeerNgEpeIngrStatsEntry 82 }

tBgpPeerNgAdjSid27StatsPktCnt    OBJECT-TYPE
    SYNTAX      Counter64
    MAX-ACCESS  read-only
    STATUS      current
    DESCRIPTION
        "The value of tBgpPeerNgAdjSid27StatsPktCnt indicates the number of
         packets for this peer."
    ::= { tBgpPeerNgEpeIngrStatsEntry 83 }

tBgpPeerNgAdjSid27StatsByteCnt   OBJECT-TYPE
    SYNTAX      Counter64
    MAX-ACCESS  read-only
    STATUS      current
    DESCRIPTION
        "The value of tBgpPeerNgAdjSid27StatsByteCnt indicates the number of
         bytes for this peer."
    ::= { tBgpPeerNgEpeIngrStatsEntry 84 }

tBgpPeerNgAdjSid28Value          OBJECT-TYPE
    SYNTAX      Unsigned32
    MAX-ACCESS  read-only
    STATUS      current
    DESCRIPTION
        "The value of tBgpPeerNgAdjSid28Value specifies the adjacent sid value."
    ::= { tBgpPeerNgEpeIngrStatsEntry 85 }

tBgpPeerNgAdjSid28StatsPktCnt    OBJECT-TYPE
    SYNTAX      Counter64
    MAX-ACCESS  read-only
    STATUS      current
    DESCRIPTION
        "The value of tBgpPeerNgAdjSid28StatsPktCnt indicates the number of
         packets for this peer."
    ::= { tBgpPeerNgEpeIngrStatsEntry 86 }

tBgpPeerNgAdjSid28StatsByteCnt   OBJECT-TYPE
    SYNTAX      Counter64
    MAX-ACCESS  read-only
    STATUS      current
    DESCRIPTION
        "The value of tBgpPeerNgAdjSid28StatsByteCnt indicates the number of
         bytes for this peer."
    ::= { tBgpPeerNgEpeIngrStatsEntry 87 }

tBgpPeerNgAdjSid29Value          OBJECT-TYPE
    SYNTAX      Unsigned32
    MAX-ACCESS  read-only
    STATUS      current
    DESCRIPTION
        "The value of tBgpPeerNgAdjSid29Value specifies the adjacent sid value."
    ::= { tBgpPeerNgEpeIngrStatsEntry 88 }

tBgpPeerNgAdjSid29StatsPktCnt    OBJECT-TYPE
    SYNTAX      Counter64
    MAX-ACCESS  read-only
    STATUS      current
    DESCRIPTION
        "The value of tBgpPeerNgAdjSid29StatsPktCnt indicates the number of
         packets for this peer."
    ::= { tBgpPeerNgEpeIngrStatsEntry 89 }

tBgpPeerNgAdjSid29StatsByteCnt   OBJECT-TYPE
    SYNTAX      Counter64
    MAX-ACCESS  read-only
    STATUS      current
    DESCRIPTION
        "The value of tBgpPeerNgAdjSid29StatsByteCnt indicates the number of
         bytes for this peer."
    ::= { tBgpPeerNgEpeIngrStatsEntry 90 }

tBgpPeerNgAdjSid30Value          OBJECT-TYPE
    SYNTAX      Unsigned32
    MAX-ACCESS  read-only
    STATUS      current
    DESCRIPTION
        "The value of tBgpPeerNgAdjSid30Value specifies the adjacent sid value."
    ::= { tBgpPeerNgEpeIngrStatsEntry 91 }

tBgpPeerNgAdjSid30StatsPktCnt    OBJECT-TYPE
    SYNTAX      Counter64
    MAX-ACCESS  read-only
    STATUS      current
    DESCRIPTION
        "The value of tBgpPeerNgAdjSid30StatsPktCnt indicates the number of
         packets for this peer."
    ::= { tBgpPeerNgEpeIngrStatsEntry 92 }

tBgpPeerNgAdjSid30StatsByteCnt   OBJECT-TYPE
    SYNTAX      Counter64
    MAX-ACCESS  read-only
    STATUS      current
    DESCRIPTION
        "The value of tBgpPeerNgAdjSid30StatsByteCnt indicates the number of
         bytes for this peer."
    ::= { tBgpPeerNgEpeIngrStatsEntry 93 }

tBgpPeerNgAdjSid31Value          OBJECT-TYPE
    SYNTAX      Unsigned32
    MAX-ACCESS  read-only
    STATUS      current
    DESCRIPTION
        "The value of tBgpPeerNgAdjSid31Value specifies the adjacent sid value."
    ::= { tBgpPeerNgEpeIngrStatsEntry 94 }

tBgpPeerNgAdjSid31StatsPktCnt    OBJECT-TYPE
    SYNTAX      Counter64
    MAX-ACCESS  read-only
    STATUS      current
    DESCRIPTION
        "The value of tBgpPeerNgAdjSid31StatsPktCnt indicates the number of
         packets for this peer."
    ::= { tBgpPeerNgEpeIngrStatsEntry 95 }

tBgpPeerNgAdjSid31StatsByteCnt   OBJECT-TYPE
    SYNTAX      Counter64
    MAX-ACCESS  read-only
    STATUS      current
    DESCRIPTION
        "The value of tBgpPeerNgAdjSid31StatsByteCnt indicates the number of
         bytes for this peer."
    ::= { tBgpPeerNgEpeIngrStatsEntry 96 }

tBgpPeerNgAdjSid32Value          OBJECT-TYPE
    SYNTAX      Unsigned32
    MAX-ACCESS  read-only
    STATUS      current
    DESCRIPTION
        "The value of tBgpPeerNgAdjSid32Value specifies the adjacent sid value."
    ::= { tBgpPeerNgEpeIngrStatsEntry 97 }

tBgpPeerNgAdjSid32StatsPktCnt    OBJECT-TYPE
    SYNTAX      Counter64
    MAX-ACCESS  read-only
    STATUS      current
    DESCRIPTION
        "The value of tBgpPeerNgAdjSid32StatsPktCnt indicates the number of
         packets for this peer."
    ::= { tBgpPeerNgEpeIngrStatsEntry 98 }

tBgpPeerNgAdjSid32StatsByteCnt   OBJECT-TYPE
    SYNTAX      Counter64
    MAX-ACCESS  read-only
    STATUS      current
    DESCRIPTION
        "The value of tBgpPeerNgAdjSid32StatsByteCnt indicates the number of
         bytes for this peer."
    ::= { tBgpPeerNgEpeIngrStatsEntry 99 }

tBgpPeerNgSrv6TblLstCh           OBJECT-TYPE
    SYNTAX      TimeStamp
    MAX-ACCESS  read-only
    STATUS      current
    DESCRIPTION
        "The value of tBgpPeerNgSrv6TblLstCh indicates the last timestamp when
         an entry in the tBgpPeerNgSrv6Table was last changed."
    ::= { tBgpPeerObjects 19 }

tBgpPeerNgSrv6Table              OBJECT-TYPE
    SYNTAX      SEQUENCE OF TBgpPeerNgSrv6Entry
    MAX-ACCESS  not-accessible
    STATUS      current
    DESCRIPTION
        "The tBgpPeerNgSrv6Table is the list of configured objects  for
         different family types of segment-routing-v6.

         The table entries are indexed by BGP instance neighbor address  and
         family type."
    ::= { tBgpPeerObjects 20 }

tBgpPeerNgSrv6Entry              OBJECT-TYPE
    SYNTAX      TBgpPeerNgSrv6Entry
    MAX-ACCESS  not-accessible
    STATUS      current
    DESCRIPTION
        "An entry (conceptual row) in the tBgpPeerNgSrv6Table. When created,
         all objects are initialized to their default values."
    INDEX       {
        tBgpPeerNgInstanceIndex,
        tBgpPeerNgAddressType,
        tBgpPeerNgAddress,
        tBgpPeerNgSrv6Family
    }
    ::= { tBgpPeerNgSrv6Table 1 }

TBgpPeerNgSrv6Entry              ::= SEQUENCE
{
    tBgpPeerNgSrv6Family             TmnxIpFamilyIdentifier,
    tBgpPeerNgSrv6RowStatus          RowStatus,
    tBgpPeerNgSrv6LstCh              TimeStamp,
    tBgpPeerNgSrv6StripTlv           TruthValue
}

tBgpPeerNgSrv6Family             OBJECT-TYPE
    SYNTAX      TmnxIpFamilyIdentifier
    MAX-ACCESS  not-accessible
    STATUS      current
    DESCRIPTION
        "The value of tBgpPeerNgSrv6Family specifies the address family for
         which the srv6 selection applies."
    ::= { tBgpPeerNgSrv6Entry 1 }

tBgpPeerNgSrv6RowStatus          OBJECT-TYPE
    SYNTAX      RowStatus
    MAX-ACCESS  read-create
    STATUS      current
    DESCRIPTION
        "The value of tBgpPeerNgSrv6RowStatus specifies the row status for this
         table entry. It is used to create and delete row entries in this
         table."
    ::= { tBgpPeerNgSrv6Entry 2 }

tBgpPeerNgSrv6LstCh              OBJECT-TYPE
    SYNTAX      TimeStamp
    MAX-ACCESS  read-only
    STATUS      current
    DESCRIPTION
        "The value tBgpPeerNgSrv6LstCh indicates when an entry in
         tBgpPeerNgSrv6Table was last changed."
    ::= { tBgpPeerNgSrv6Entry 3 }

tBgpPeerNgSrv6StripTlv           OBJECT-TYPE
    SYNTAX      TruthValue
    MAX-ACCESS  read-create
    STATUS      current
    DESCRIPTION
        "The value of tBgpPeerNgSrv6StripTlv specifies the Srv6 TLVs need to be
         stripped  from outbound routes."
    DEFVAL      { false }
    ::= { tBgpPeerNgSrv6Entry 4 }

tBgpPeerNgAddPathsTblLstCh       OBJECT-TYPE
    SYNTAX      TimeStamp
    MAX-ACCESS  read-only
    STATUS      current
    DESCRIPTION
        "The value of tBgpPeerNgAddPathsTblLstCh indicates the last timestamp
         when an entry in the tBgpPeerNgAddPathTable was last changed."
    ::= { tBgpPeerObjects 21 }

tBgpPeerNgAddPathTable           OBJECT-TYPE
    SYNTAX      SEQUENCE OF TBgpPeerNgAddPathEntry
    MAX-ACCESS  not-accessible
    STATUS      current
    DESCRIPTION
        "tBgpPeerNgAddPathTable provides information about the attributes
         configured for the BGP instance in the peer level."
    ::= { tBgpPeerObjects 22 }

tBgpPeerNgAddPathEntry           OBJECT-TYPE
    SYNTAX      TBgpPeerNgAddPathEntry
    MAX-ACCESS  not-accessible
    STATUS      current
    DESCRIPTION
        "An entry in the tBgpPeerNgAddPathEntry. Each entry maintains the
         attributes configured for BGP instance."
    INDEX       {
        tBgpPeerNgInstanceIndex,
        tBgpPeerNgAddressType,
        tBgpPeerNgAddress
    }
    ::= { tBgpPeerNgAddPathTable 1 }

TBgpPeerNgAddPathEntry           ::= SEQUENCE
{
    tBgpPeerNgAddPathInheritance     TruthValue,
    tBgpPeerNgAddPathsRowStatus      RowStatus,
    tBgpPeerNgAddPathsLstCh          TimeStamp,
    tBgpPeerNgAddPathRecv            TmnxAddPathAddressFamily,
    tBgpPeerNgAddPathIpv4Limit       TmnxAddPathSendLimit,
    tBgpPeerNgAddPathVpnIpv4Limit    TmnxAddPathSendLimit,
    tBgpPeerNgAddPathIpv6Limit       TmnxAddPathSendLimit,
    tBgpPeerNgAddPathVpnIpv6Limit    TmnxAddPathSendLimit,
    tBgpPeerNgAddPathLblIpv4Limit    TmnxAddPathSendLimit,
    tBgpPeerNgAddPathLblIpv6Limit    TmnxAddPathSendLimit,
    tBgpPeerNgAddPathMvpnIpv4Limit   Integer32,
    tBgpPeerNgAddPathMvpnIpv6Limit   Integer32,
    tBgpPeerNgAddPathMcastVpnV4Limit Integer32,
    tBgpPeerNgAddPathMcastVpnV6Limit Integer32,
    tBgpPeerNgAddPathEvpnLimit       TmnxAddPathSendLimit
}

tBgpPeerNgAddPathInheritance     OBJECT-TYPE
    SYNTAX      TruthValue
    MAX-ACCESS  read-only
    STATUS      current
    DESCRIPTION
        "The value of tBgpPeerNgAddPathInheritance specifies if the peer entry
         in this row, should inherit the operational value of an object, or use
         the administratively set value.

         When the value is 'false', then the object's administrative and
         operational value are whatever the DEFVAL or most recently SET value
         is.

         When the value is 'true', then the object's administrative and
         operational value are inherited from the corresponding object in
         tBgpPeerNgAddPathTable."
    DEFVAL      { true }
    ::= { tBgpPeerNgAddPathEntry 1 }

tBgpPeerNgAddPathsRowStatus      OBJECT-TYPE
    SYNTAX      RowStatus
    MAX-ACCESS  read-create
    STATUS      current
    DESCRIPTION
        "The value of tBgpPeerNgAddPathsRowStatus specifies the row status for
         this table entry. It is used to create and delete row entries in this
         table."
    ::= { tBgpPeerNgAddPathEntry 3 }

tBgpPeerNgAddPathsLstCh          OBJECT-TYPE
    SYNTAX      TimeStamp
    MAX-ACCESS  read-only
    STATUS      current
    DESCRIPTION
        "The value tBgpPeerNgAddPathsLstCh indicates when an entry in
         tBgpPeerNgAddPathTable was last changed."
    ::= { tBgpPeerNgAddPathEntry 4 }

tBgpPeerNgAddPathRecv            OBJECT-TYPE
    SYNTAX      TmnxAddPathAddressFamily
    MAX-ACCESS  read-create
    STATUS      current
    DESCRIPTION
        "The value of tBgpPeerNgAddPathRecv specifies the address families
         which are enabled to receive BGP ADD-PATH on this BGP peer.

         ADD-PATH allows a BGP router to receive multiple distinct paths for
         the same prefix/NLRI (Network Layer Reachability Information)."
    DEFVAL      { {none} }
    ::= { tBgpPeerNgAddPathEntry 5 }

tBgpPeerNgAddPathIpv4Limit       OBJECT-TYPE
    SYNTAX      TmnxAddPathSendLimit
    MAX-ACCESS  read-create
    STATUS      current
    DESCRIPTION
        "The value of tBgpPeerNgAddPathIpv4Limit specifies the maximum number
         of paths per IPv4 prefix that can be advertised to ADD-PATH peers on
         this BGP peer.

         An 'inconsistentValue' error is returned if an attempt is made to set
         this object to a value greater than tBgpInstanceMultipathBgp."
    DEFVAL      { 0 }
    ::= { tBgpPeerNgAddPathEntry 6 }

tBgpPeerNgAddPathVpnIpv4Limit    OBJECT-TYPE
    SYNTAX      TmnxAddPathSendLimit
    MAX-ACCESS  read-create
    STATUS      current
    DESCRIPTION
        "The value of tBgpPeerNgAddPathVpnIpv4Limit specifies the maximum
         number of paths per VPN IPv4 prefix that can be advertised to ADD-PATH
         peers on this BGP peer.

         An 'inconsistentValue' error is returned if an attempt is made to set
         this object to a value greater than tBgpInstanceMultipathBgp."
    DEFVAL      { 0 }
    ::= { tBgpPeerNgAddPathEntry 7 }

tBgpPeerNgAddPathIpv6Limit       OBJECT-TYPE
    SYNTAX      TmnxAddPathSendLimit
    MAX-ACCESS  read-create
    STATUS      current
    DESCRIPTION
        "The value of tBgpPeerNgAddPathIpv6Limit specifies the maximum number
         of paths per IPv6 prefix that can be advertised to ADD-PATH peers on
         this BGP peer.

         An 'inconsistentValue' error is returned if an attempt is made to set
         this object to a value greater than tBgpInstanceMultipathBgp."
    DEFVAL      { 0 }
    ::= { tBgpPeerNgAddPathEntry 8 }

tBgpPeerNgAddPathVpnIpv6Limit    OBJECT-TYPE
    SYNTAX      TmnxAddPathSendLimit
    MAX-ACCESS  read-create
    STATUS      current
    DESCRIPTION
        "The value of tBgpPeerNgAddPathVpnIpv6Limit specifies the maximum
         number of paths per VPN IPv6 prefix that can be advertised to ADD-PATH
         peers on this BGP peer.

         An 'inconsistentValue' error is returned if an attempt is made to set
         this object to a value greater than tBgpInstanceMultipath."
    DEFVAL      { 0 }
    ::= { tBgpPeerNgAddPathEntry 9 }

tBgpPeerNgAddPathLblIpv4Limit    OBJECT-TYPE
    SYNTAX      TmnxAddPathSendLimit
    MAX-ACCESS  read-create
    STATUS      current
    DESCRIPTION
        "The value of tBgpPeerNgAddPathLblIpv4Limit specifies the maximum
         number of paths per label IPv4 prefix that can be advertised to
         ADD-PATH peers on this BGP peer.

         An 'inconsistentValue' error is returned if an attempt is made to set
         this object to a value greater than tBgpInstanceMultipathBgp."
    DEFVAL      { 0 }
    ::= { tBgpPeerNgAddPathEntry 10 }

tBgpPeerNgAddPathLblIpv6Limit    OBJECT-TYPE
    SYNTAX      TmnxAddPathSendLimit
    MAX-ACCESS  read-create
    STATUS      current
    DESCRIPTION
        "The value of tBgpPeerNgAddPathLblIpv6Limit specifies the maximum
         number of paths per label IPv6 prefix that can be advertised to
         ADD-PATH peers on this BGP peer.

         An 'inconsistentValue' error is returned if an attempt is made to set
         this object to a value greater than tBgpInstanceMultipathBgp."
    DEFVAL      { 0 }
    ::= { tBgpPeerNgAddPathEntry 11 }

tBgpPeerNgAddPathMvpnIpv4Limit   OBJECT-TYPE
    SYNTAX      Integer32 (0..16)
    MAX-ACCESS  read-create
    STATUS      current
    DESCRIPTION
        "The value of tBgpPeerNgAddPathMvpnIpv4Limit specifies the maximum
         number of paths per MVPN IPv4 prefix that can be advertised to
         ADD-PATH peers on this BGP peer.

         An 'inconsistentValue' error is returned if an attempt is made to set
         this object to a value greater than tBgpInstanceMultipathBgp."
    DEFVAL      { 0 }
    ::= { tBgpPeerNgAddPathEntry 12 }

tBgpPeerNgAddPathMvpnIpv6Limit   OBJECT-TYPE
    SYNTAX      Integer32 (0..16)
    MAX-ACCESS  read-create
    STATUS      current
    DESCRIPTION
        "The value of tBgpPeerNgAddPathMvpnIpv6Limit specifies the maximum
         number of paths per MVPN IPv6 prefix that can be advertised to
         ADD-PATH peers on this BGP peer.

         An 'inconsistentValue' error is returned if an attempt is made to set
         this object to a value greater than tBgpInstanceMultipathBgp."
    DEFVAL      { 0 }
    ::= { tBgpPeerNgAddPathEntry 13 }

tBgpPeerNgAddPathMcastVpnV4Limit OBJECT-TYPE
    SYNTAX      Integer32 (0..16)
    MAX-ACCESS  read-create
    STATUS      current
    DESCRIPTION
        "The value of tBgpPeerNgAddPathMcastVpnV4Limit specifies the maximum
         number of paths per Mcast VPN IPv4 prefix that can be advertised to
         ADD-PATH peers on this BGP peer.

         An 'inconsistentValue' error is returned if an attempt is made to set
         this object to a value greater than tBgpInstanceMultipathBgp."
    DEFVAL      { 0 }
    ::= { tBgpPeerNgAddPathEntry 14 }

tBgpPeerNgAddPathMcastVpnV6Limit OBJECT-TYPE
    SYNTAX      Integer32 (0..16)
    MAX-ACCESS  read-create
    STATUS      current
    DESCRIPTION
        "The value of tBgpPeerNgAddPathMcastVpnV6Limit specifies the maximum
         number of paths per Mcast VPN IPv6 prefix that can be advertised to
         ADD-PATH peers on this BGP peer.

         An 'inconsistentValue' error is returned if an attempt is made to set
         this object to a value greater than tBgpInstanceMultipath."
    DEFVAL      { 0 }
    ::= { tBgpPeerNgAddPathEntry 15 }

tBgpPeerNgAddPathEvpnLimit       OBJECT-TYPE
    SYNTAX      TmnxAddPathSendLimit
    MAX-ACCESS  read-create
    STATUS      current
    DESCRIPTION
        "The value of tBgpPeerNgAddPathEvpnLimit specifies the maximum number
         of paths per MVPN IPv4 prefix that can be advertised to ADD-PATH peers
         on this BGP peer.

         An 'inconsistentValue' error is returned if an attempt is made to set
         this object to a value greater than tBgpInstanceMultipathBgp."
    DEFVAL      { 0 }
    ::= { tBgpPeerNgAddPathEntry 16 }

tBgpPeerAFStatsTable             OBJECT-TYPE
    SYNTAX      SEQUENCE OF TBgpPeerAFStatsEntry
    MAX-ACCESS  not-accessible
    STATUS      current
    DESCRIPTION
        "The tBgpPeerAFStatsTable contains statistics information for peer
         level per family."
    ::= { tBgpPeerObjects 23 }

tBgpPeerAFStatsEntry             OBJECT-TYPE
    SYNTAX      TBgpPeerAFStatsEntry
    MAX-ACCESS  not-accessible
    STATUS      current
    DESCRIPTION
        "Defines an entry (conceptual row) in the tBgpPeerAFStatsTable"
    INDEX       {
        tBgpPeerNgInstanceIndex,
        tBgpPeerNgAddressType,
        tBgpPeerNgAddress,
        tBgpPeerAFStatsFamily
    }
    ::= { tBgpPeerAFStatsTable 1 }

TBgpPeerAFStatsEntry             ::= SEQUENCE
{
    tBgpPeerAFStatsFamily            TmnxIpFamilyIdentifier,
    tBgpPeerAFStatsHeldExcessPfxs    Counter32
}

tBgpPeerAFStatsFamily            OBJECT-TYPE
    SYNTAX      TmnxIpFamilyIdentifier
    MAX-ACCESS  not-accessible
    STATUS      current
    DESCRIPTION
        "The value of tBgpPeerAFStatsFamily specifies the address family for
         which the peer stats applies."
    ::= { tBgpPeerAFStatsEntry 1 }

tBgpPeerAFStatsHeldExcessPfxs    OBJECT-TYPE
    SYNTAX      Counter32
    MAX-ACCESS  read-only
    STATUS      current
    DESCRIPTION
        "The value of tBgpPeerAFStatsHeldExcessPfxs indicates the number of
         routes that have  been received from the peer that are in the
         excess-inactive state"
    ::= { tBgpPeerAFStatsEntry 2 }

tBgpInstanceConfederationObjects OBJECT IDENTIFIER ::= { tBgpObjects 5 }

tBgpConfederationTableLastChanged OBJECT-TYPE
    SYNTAX      TimeStamp
    MAX-ACCESS  read-only
    STATUS      obsolete
    DESCRIPTION
        "The value of tBgpConfederationTableLastChanged indicates the last
         timestamp when an entry in the tBgpPeerGroupTable was last changed."
    ::= { tBgpInstanceConfederationObjects 1 }

tBgpConfederationTable           OBJECT-TYPE
    SYNTAX      SEQUENCE OF TBgpConfederationEntry
    MAX-ACCESS  not-accessible
    STATUS      obsolete
    DESCRIPTION
        "tBgpConfederationTable consists of information about each
         confederation member for every running instance of BGP.

         This table was obsoleted in release 7.0.  It is replaced with the
         tBgpConfederation4ByteTable to support 4-byte AS number."
    ::= { tBgpInstanceConfederationObjects 2 }

tBgpConfederationEntry           OBJECT-TYPE
    SYNTAX      TBgpConfederationEntry
    MAX-ACCESS  not-accessible
    STATUS      obsolete
    DESCRIPTION
        "An entry (conceptual row) in the tBgpConfederationTable. each entry
         represents a confederation member for the instance of BGP running on
         the virtual router."
    INDEX       {
        tBgpInstanceIndex,
        tBgpConfederationAS,
        tBgpConfederationMemberAS
    }
    ::= { tBgpConfederationTable 1 }

TBgpConfederationEntry           ::= SEQUENCE
{
    tBgpConfederationAS              TmnxBgpAutonomousSystem,
    tBgpConfederationMemberAS        TmnxBgpAutonomousSystem,
    tBgpConfederationRowStatus       RowStatus
}

tBgpConfederationAS              OBJECT-TYPE
    SYNTAX      TmnxBgpAutonomousSystem
    MAX-ACCESS  not-accessible
    STATUS      obsolete
    DESCRIPTION
        "The value of tBgpConfederationAS is the secondary index of
         tBgpConfederationTable, each confederation entry is differentiated by
         autonomous system number."
    ::= { tBgpConfederationEntry 1 }

tBgpConfederationMemberAS        OBJECT-TYPE
    SYNTAX      TmnxBgpAutonomousSystem
    MAX-ACCESS  not-accessible
    STATUS      obsolete
    DESCRIPTION
        "The value of tBgpConfederationMemberAS is the tertiary index for
         tBgpConfederationTable, each confederation member entry is
         differentiated by autonomous system number."
    ::= { tBgpConfederationEntry 2 }

tBgpConfederationRowStatus       OBJECT-TYPE
    SYNTAX      RowStatus
    MAX-ACCESS  read-create
    STATUS      obsolete
    DESCRIPTION
        "The value of tBgpConfederationRowStatus specifies the row status
         object of the BGP confederation entry for the virtual router.

         Use row status to create and destroy entries."
    ::= { tBgpConfederationEntry 3 }

tBgpConfederation4BytTblLstChngd OBJECT-TYPE
    SYNTAX      TimeStamp
    MAX-ACCESS  read-only
    STATUS      current
    DESCRIPTION
        "The value of tBgpConfederation4BytTblLstChngd indicates the time of
         the last change to any row of tBgpConfederation4ByteTable."
    ::= { tBgpInstanceConfederationObjects 3 }

tBgpConfederation4ByteTable      OBJECT-TYPE
    SYNTAX      SEQUENCE OF TBgpConfederation4ByteEntry
    MAX-ACCESS  not-accessible
    STATUS      current
    DESCRIPTION
        "The tBgpConfederation4ByteTable has an entry for each confederation
         member. This table holds information about each confederation member
         for every running instance of BGP."
    ::= { tBgpInstanceConfederationObjects 4 }

tBgpConfederation4ByteEntry      OBJECT-TYPE
    SYNTAX      TBgpConfederation4ByteEntry
    MAX-ACCESS  not-accessible
    STATUS      current
    DESCRIPTION
        "An entry (conceptual row) in the tBgpConfederation4ByteTable. Each row
         entry represents a confederation member for the instance of BGP
         running on the virtual router."
    INDEX       {
        tBgpInstanceIndex,
        tBgpConfederation4ByteAS,
        tBgpConfederation4ByteMemberAS
    }
    ::= { tBgpConfederation4ByteTable 1 }

TBgpConfederation4ByteEntry      ::= SEQUENCE
{
    tBgpConfederation4ByteAS         InetAutonomousSystemNumber,
    tBgpConfederation4ByteMemberAS   InetAutonomousSystemNumber,
    tBgpConfederation4ByteRowStatus  RowStatus
}

tBgpConfederation4ByteAS         OBJECT-TYPE
    SYNTAX      InetAutonomousSystemNumber
    MAX-ACCESS  not-accessible
    STATUS      current
    DESCRIPTION
        "The value of tBgpConfederation4ByteAS specifies the secondary index
         for tBgpConfederation4ByteTable. Each confederation entry is
         differentiated by autonomous system number."
    ::= { tBgpConfederation4ByteEntry 1 }

tBgpConfederation4ByteMemberAS   OBJECT-TYPE
    SYNTAX      InetAutonomousSystemNumber
    MAX-ACCESS  not-accessible
    STATUS      current
    DESCRIPTION
        "The value of tBgpConfederation4ByteMemberAS specifies the tertiary
         index for tBgpConfederation4ByteTable. Each confederation member entry
         is differentiated by autonomous system number."
    ::= { tBgpConfederation4ByteEntry 2 }

tBgpConfederation4ByteRowStatus  OBJECT-TYPE
    SYNTAX      RowStatus
    MAX-ACCESS  read-create
    STATUS      current
    DESCRIPTION
        "The value of tBgpConfederation4ByteRowStatus specifies the row status
         of the BGP confederation entry for the virtual router. Row status is
         used for creation and deletion of tBgpConfederation4ByteTable entries."
    ::= { tBgpConfederation4ByteEntry 3 }

tBgpPeeringPolicyObjects         OBJECT IDENTIFIER ::= { tBgpObjects 6 }

tBgpPeeringPolicyTableLastChngd  OBJECT-TYPE
    SYNTAX      TimeStamp
    MAX-ACCESS  read-only
    STATUS      current
    DESCRIPTION
        "The value of tBgpPeeringPolicyTableLastChngd indicates the sysUpTime
         when any type of change was last made to the tBgpPeeringPolicyTable."
    ::= { tBgpPeeringPolicyObjects 1 }

tBgpPeeringPolicyTable           OBJECT-TYPE
    SYNTAX      SEQUENCE OF TBgpPeeringPolicyEntry
    MAX-ACCESS  not-accessible
    STATUS      current
    DESCRIPTION
        "The tBgpPeeringPolicyTable table contains BGP peering policy
         definitions."
    ::= { tBgpPeeringPolicyObjects 2 }

tBgpPeeringPolicyEntry           OBJECT-TYPE
    SYNTAX      TBgpPeeringPolicyEntry
    MAX-ACCESS  not-accessible
    STATUS      current
    DESCRIPTION
        "An entry (conceptual row) in the tBgpPeeringPolicyTable. Each entry
         contains all data for a given BGP peering policy. Entries are
         created/modified/deleted by SNMP GET/SETs."
    INDEX       { IMPLIED tBgpPeeringPolicyName }
    ::= { tBgpPeeringPolicyTable 1 }

TBgpPeeringPolicyEntry           ::= SEQUENCE
{
    tBgpPeeringPolicyName            TNamedItem,
    tBgpPrngPlcyRowStatus            RowStatus,
    tBgpPrngPlcyLastChngd            TimeStamp,
    tBgpPrngPlcyDescription          DisplayString,
    tBgpPrngPlcyInheritance          Counter64,
    tBgpPrngPlcyAdvertiseInactiveRts TruthValue,
    tBgpPrngPlcyNoAggregatorID       TruthValue,
    tBgpPrngPlcyASOverride           TruthValue,
    tBgpPrngPlcyAuthKeyChain         TNamedItemOrEmpty,
    tBgpPrngPlcyMd5Auth              TruthValue,
    tBgpPrngPlcyMd5AuthKey           DisplayString,
    tBgpPrngPlcyClusterId            IpAddress,
    tBgpPrngPlcyConnectRetry         BgpConnectRetryTime,
    tBgpPrngPlcyDampening            TruthValue,
    tBgpPrngPlcyDisableClientReflect TruthValue,
    tBgpPrngPlcyDisableComms         TruthValue,
    tBgpPrngPlcyDisableExtComms      TruthValue,
    tBgpPrngPlcyDisableFEFailover    TruthValue,
    tBgpPrngPlcyImportPolicy1        TPolicyStatementNameOrEmpty,
    tBgpPrngPlcyImportPolicy2        TPolicyStatementNameOrEmpty,
    tBgpPrngPlcyImportPolicy3        TPolicyStatementNameOrEmpty,
    tBgpPrngPlcyImportPolicy4        TPolicyStatementNameOrEmpty,
    tBgpPrngPlcyImportPolicy5        TPolicyStatementNameOrEmpty,
    tBgpPrngPlcyExportPolicy1        TPolicyStatementNameOrEmpty,
    tBgpPrngPlcyExportPolicy2        TPolicyStatementNameOrEmpty,
    tBgpPrngPlcyExportPolicy3        TPolicyStatementNameOrEmpty,
    tBgpPrngPlcyExportPolicy4        TPolicyStatementNameOrEmpty,
    tBgpPrngPlcyExportPolicy5        TPolicyStatementNameOrEmpty,
    tBgpPrngPlcyHoldTime             BgpHoldTime,
    tBgpPrngPlcyKeepAlive            BgpKeepAliveTime,
    tBgpPrngPlcyLocalAddressType     InetAddressType,
    tBgpPrngPlcyLocalAddress         InetAddress,
    tBgpPrngPlcyLocalAS              InetAutonomousSystemNumber,
    tBgpPrngPlcyLocalASPrivate       TruthValue,
    tBgpPrngPlcyLocalPreference      TmnxBgpLocalPreference,
    tBgpPrngPlcyLoopDetect           BgpLoopDetect,
    tBgpPrngPlcyMEDSource            BgpMEDSource,
    tBgpPrngPlcyMEDValue             BgpMEDValue,
    tBgpPrngPlcyMinASOrigination     BgpMinASOriginationTime,
    tBgpPrngPlcyMinRteAdvertisement  BgpMinRouteAdvertisement,
    tBgpPrngPlcyMultihop             BgpTimeToLive,
    tBgpPrngPlcyNextHopSelf          TruthValue,
    tBgpPrngPlcyPassive              TruthValue,
    tBgpPrngPlcyPeerAS               InetAutonomousSystemNumber,
    tBgpPrngPlcyPreference           TmnxBgpPreference,
    tBgpPrngPlcyMaxPrefix            BgpPrefixLimit,
    tBgpPrngPlcyRemovePrivateAS      TruthValue,
    tBgpPrngPlcyMinTTLValue          Unsigned32,
    tBgpPrngPlcyPeerType             BgpPeerType,
    tBgpPrngPlcyDisable4ByteASN      TruthValue,
    tBgpPrngPlcyRemovePrivateASLmtd  TruthValue,
    tBgpPrngPlcyMaxPrefixLogOnly     TruthValue,
    tBgpPrngPlcyMaxPrefixThreshold   Unsigned32,
    tBgpPrngPlcyBfdEnable            TruthValue,
    tBgpPrngPlcyFamilyIpv4           TruthValue,
    tBgpPrngPlcyFamilyIpv6           TruthValue
}

tBgpPeeringPolicyName            OBJECT-TYPE
    SYNTAX      TNamedItem
    MAX-ACCESS  not-accessible
    STATUS      current
    DESCRIPTION
        "Index for the tBgpPeeringPolicyTable. The value of
         tBgpPeeringPolicyName specifies the name of the bgp peering policy
         defined by this row."
    ::= { tBgpPeeringPolicyEntry 1 }

tBgpPrngPlcyRowStatus            OBJECT-TYPE
    SYNTAX      RowStatus
    MAX-ACCESS  read-create
    STATUS      current
    DESCRIPTION
        "The value of the object tBgpPrngPlcyRowStatus specifies the RowStatus
         for the Bgp Peering Policy Entry."
    ::= { tBgpPeeringPolicyEntry 2 }

tBgpPrngPlcyLastChngd            OBJECT-TYPE
    SYNTAX      TimeStamp
    MAX-ACCESS  read-only
    STATUS      current
    DESCRIPTION
        "The value of the object tBgpPrngPlcyLastChngd indicates the value of
         the sysUpTime when this entry was last modified."
    ::= { tBgpPeeringPolicyEntry 3 }

tBgpPrngPlcyDescription          OBJECT-TYPE
    SYNTAX      DisplayString (SIZE (0..80))
    MAX-ACCESS  read-create
    STATUS      current
    DESCRIPTION
        "The value of tBgpPrngPlcyDescription specifies a user provided
         description string for this BGP peering policy. It can consist of any
         printable, seven-bit ASCII characters up to 80 characters in length."
    DEFVAL      { ''H }
    ::= { tBgpPeeringPolicyEntry 4 }

tBgpPrngPlcyInheritance          OBJECT-TYPE
    SYNTAX      Counter64
    MAX-ACCESS  read-create
    STATUS      current
    DESCRIPTION
        "tBgpPrngPlcyInheritance is a bit-mask, with the following positions:

         tBgpPrngPlcyAdvertiseInactiveRts   0x00000008
         tBgpPrngPlcyNoAggregatorID         0x00000010
         tBgpPrngPlcyASOverride             0x00000020
         tBgpPrngPlcyAuthKeyChain           0x00000040
         tBgpPrngPlcyMd5Auth                0x00000080
         tBgpPrngPlcyMd5AuthKey             0x00000100
         tBgpPrngPlcyClusterId              0x00000200
         tBgpPrngPlcyConnectRetry           0x00000400
         tBgpPrngPlcyDampening              0x00000800
         tBgpPrngPlcyDisableClientReflect   0x00001000
         tBgpPrngPlcyDisableComms           0x00002000
         tBgpPrngPlcyDisableExtComms        0x00004000
         tBgpPrngPlcyDisableFEFailover      0x00008000
         tBgpPrngPlcyImportPolicy1          0x00010000
         tBgpPrngPlcyImportPolicy2          0x00020000
         tBgpPrngPlcyImportPolicy3          0x00040000
         tBgpPrngPlcyImportPolicy4          0x00080000
         tBgpPrngPlcyImportPolicy5          0x00100000
         tBgpPrngPlcyExportPolicy1          0x00200000
         tBgpPrngPlcyExportPolicy2          0x00400000
         tBgpPrngPlcyExportPolicy3          0x00800000
         tBgpPrngPlcyExportPolicy4          0x01000000
         tBgpPrngPlcyExportPolicy5          0x02000000
         tBgpPrngPlcyHoldTime               0x04000000
         tBgpPrngPlcyKeepAlive              0x08000000
         tBgpPrngPlcyLocalAddressType       0x10000000
         tBgpPrngPlcyLocalAddress           0x20000000
         tBgpPrngPlcyLocalAS                0x40000000
         tBgpPrngPlcyLocalASPrivate         0x80000000
         tBgpPrngPlcyLocalPreference        0x0000000100000000
         tBgpPrngPlcyLoopDetect             0x0000000200000000
         tBgpPrngPlcyMEDSource              0x0000000400000000
         tBgpPrngPlcyMEDValue               0x0000000800000000
         obsoleted tBgpPrngPlcyMinASOrigination       0x0000001000000000
         tBgpPrngPlcyMinRteAdvertisement    0x0000002000000000
         tBgpPrngPlcyMultihop               0x0000004000000000
         tBgpPrngPlcyNextHopSelf            0x0000008000000000
         tBgpPrngPlcyPassive                0x0000010000000000
         tBgpPrngPlcyPeerAS                 0x0000020000000000
         tBgpPrngPlcyPreference             0x0000040000000000
         tBgpPrngPlcyMaxPrefix              0x0000080000000000
         tBgpPrngPlcyRemovePrivateAS        0x0000100000000000
         tBgpPrngPlcyMinTTLValue            0x0000200000000000
         tBgpPrngPlcyPeerType               0x0000400000000000
         tBgpPrngPlcyDisable4ByteASN        0x0000800000000000
         tBgpPrngPlcyRemovePrivateASLmtd    0x0001000000000000
         tBgpPrngPlcyMaxPrefixLogOnly       0x0002000000000000
         tBgpPrngPlcyMaxPrefixThreshold     0x0004000000000000
         tBgpPrngPlcyBfdEnable              0x0008000000000000
         When the bit for an object is set to one, then the
         object's administrative and operational value are whatever
         the DEFVAL or most recently SET value is.

         When the bit for an object is set to zero, then the bgp peer created
         with this policy administrative and operational value are inherited
         from the corresponding object in tBgpPeerGroupTable, or from the
         corresponding object in tBgpInstanceTable."
    DEFVAL      { 0 }
    ::= { tBgpPeeringPolicyEntry 5 }

tBgpPrngPlcyAdvertiseInactiveRts OBJECT-TYPE
    SYNTAX      TruthValue
    MAX-ACCESS  read-create
    STATUS      current
    DESCRIPTION
        "The value of the object tBgpPrngPlcyAdvertiseInactiveRts specifies
         whether or not the advertising of inactive BGP routes to other BGP
         peers is allowed."
    DEFVAL      { false }
    ::= { tBgpPeeringPolicyEntry 6 }

tBgpPrngPlcyNoAggregatorID       OBJECT-TYPE
    SYNTAX      TruthValue
    MAX-ACCESS  read-create
    STATUS      current
    DESCRIPTION
        "The value of the object tBgpPrngPlcyNoAggregatorID specifies whether
         or not the router ID in the BGP aggregator path attribute is set to
         zero.

         When set to 'true' the router ID in the BGP aggregator path attribute
         is set to zero.

         Doing this prevents different routers within an AS from creating
         aggregate routes that contain different AS paths. The default is to
         set the Aggregator ID to the router's BGP ID."
    DEFVAL      { false }
    ::= { tBgpPeeringPolicyEntry 7 }

tBgpPrngPlcyASOverride           OBJECT-TYPE
    SYNTAX      TruthValue
    MAX-ACCESS  read-create
    STATUS      current
    DESCRIPTION
        "The value of the object tBgpPrngPlcyASOverride specifies whether or
         not the customer AS number in the ASPATH attribute is overridden with
         the own AS number.

         When the value of tBgpPrngPlcyASOverride is 'true', the service
         provider BGP will override the customer AS number in the ASPATH with
         its own AS number. Without this feature there could be scenarios where
         multiple CE locations belonging to the same AS will not be able to
         communicate due to a potential loop detection."
    DEFVAL      { false }
    ::= { tBgpPeeringPolicyEntry 8 }

tBgpPrngPlcyAuthKeyChain         OBJECT-TYPE
    SYNTAX      TNamedItemOrEmpty
    MAX-ACCESS  read-create
    STATUS      current
    DESCRIPTION
        "The value of tBgpPrngPlcyAuthKeyChain specifies the keychain which
         will be used to sign and/or authenticate the BGP protocol stream.

         The keychain name is defined by tmnxKeyChainName and is the index for
         TIMETRA-SECURITY-MIB::tmnxKeyChainTable"
    DEFVAL      { ''H }
    ::= { tBgpPeeringPolicyEntry 9 }

tBgpPrngPlcyMd5Auth              OBJECT-TYPE
    SYNTAX      TruthValue
    MAX-ACCESS  read-create
    STATUS      current
    DESCRIPTION
        "The value of the object tBgpPrngPlcyMd5Auth specifies whether or not
         authentication using MD5 message based digest protocol is enabled."
    DEFVAL      { false }
    ::= { tBgpPeeringPolicyEntry 10 }

tBgpPrngPlcyMd5AuthKey           OBJECT-TYPE
    SYNTAX      DisplayString (SIZE (0..255))
    MAX-ACCESS  read-create
    STATUS      current
    DESCRIPTION
        "The value of the object tBgpPrngPlcyMd5AuthKey specifies the
         authentication key to be used between BGP peers neighbors when
         establishing sessions.

         Authentication is done using the MD5 message based digest protocol.
         Authentication can be configured globally and applied to all
         BGP peers or per group or per peer.  The most specific value
         is used.
         The authentication key can be any combination of letters or
         numbers.  Note that the string CANNOT contain embedded nulls."
    DEFVAL      { ''H }
    ::= { tBgpPeeringPolicyEntry 11 }

tBgpPrngPlcyClusterId            OBJECT-TYPE
    SYNTAX      IpAddress
    MAX-ACCESS  read-create
    STATUS      current
    DESCRIPTION
        "The value of the object tBgpPrngPlcyClusterId specifies the cluster ID
         for a route reflector server.

         A value of 0.0.0.0 indicates that no cluster ID has been assigned to
         the BGP instance."
    DEFVAL      { '00000000'H }
    ::= { tBgpPeeringPolicyEntry 12 }

tBgpPrngPlcyConnectRetry         OBJECT-TYPE
    SYNTAX      BgpConnectRetryTime
    UNITS       "seconds"
    MAX-ACCESS  read-create
    STATUS      current
    DESCRIPTION
        "The value of the object tBgpPrngPlcyConnectRetry specifies the value
         (in seconds) of the BGP Connect Retry timer."
    REFERENCE
        "BGP4-MIB.bgpPeerConnectRetryInterval"
    DEFVAL      { 120 }
    ::= { tBgpPeeringPolicyEntry 13 }

tBgpPrngPlcyDampening            OBJECT-TYPE
    SYNTAX      TruthValue
    MAX-ACCESS  read-create
    STATUS      current
    DESCRIPTION
        "The value of the object tBgpPrngPlcyDampening specifies whether or not
         route dampening should be applied to learned routes."
    DEFVAL      { false }
    ::= { tBgpPeeringPolicyEntry 14 }

tBgpPrngPlcyDisableClientReflect OBJECT-TYPE
    SYNTAX      TruthValue
    MAX-ACCESS  read-create
    STATUS      current
    DESCRIPTION
        "The value of the object tBgpPrngPlcyDisableClientReflect specifies
         whether or not route reflection is active for this peer.

         Setting this value to 'true', disables reflection of routes by the
         route reflector to all client peers within its cluster. When set to
         'false', reflection of routes to all client peers is enabled."
    DEFVAL      { false }
    ::= { tBgpPeeringPolicyEntry 15 }

tBgpPrngPlcyDisableComms         OBJECT-TYPE
    SYNTAX      TruthValue
    MAX-ACCESS  read-create
    STATUS      current
    DESCRIPTION
        "The value of the object tBgpPrngPlcyDisableComms specifies whether or
         not the community attribute is to be sent to the peer for non-external
         communities.

         Setting the value of tBgpPGDisableComms to 'true' disables sending of
         community attribute to the peer for non-external communities."
    DEFVAL      { false }
    ::= { tBgpPeeringPolicyEntry 16 }

tBgpPrngPlcyDisableExtComms      OBJECT-TYPE
    SYNTAX      TruthValue
    MAX-ACCESS  read-create
    STATUS      current
    DESCRIPTION
        "The value of the object tBgpPrngPlcyDisableExtComms specifies whether
         or not the community attribute is to be sent to the peer for external
         communities.

         Setting the value of tBgpPGDisableComms to 'true' disables sending of
         community attribute to the peers for external communities."
    DEFVAL      { false }
    ::= { tBgpPeeringPolicyEntry 17 }

tBgpPrngPlcyDisableFEFailover    OBJECT-TYPE
    SYNTAX      TruthValue
    MAX-ACCESS  read-create
    STATUS      current
    DESCRIPTION
        "The value of the object tBgpPrngPlcyDisableFEFailover specifies
         whether or not the router should drop an external BGP session
         immediately when the local interface goes down, or whether the BGP
         session should be kept up until the holdtime expires.

         Setting the value to 'true' causes the external BGP session to go down
         immediately when the local interface goes down."
    DEFVAL      { false }
    ::= { tBgpPeeringPolicyEntry 18 }

tBgpPrngPlcyImportPolicy1        OBJECT-TYPE
    SYNTAX      TPolicyStatementNameOrEmpty
    MAX-ACCESS  read-create
    STATUS      obsolete
    DESCRIPTION
        "The value of the object tBgpPrngPlcyImportPolicy1 specifies the import
         policy number 1 for this peer.

         An empty string indicates that no import policy is applied.

         This object was obsoleted in release 10.0. It is replaced by object
         tBgpPeeringPlcyImportPolicy1."
    DEFVAL      { ''H }
    ::= { tBgpPeeringPolicyEntry 19 }

tBgpPrngPlcyImportPolicy2        OBJECT-TYPE
    SYNTAX      TPolicyStatementNameOrEmpty
    MAX-ACCESS  read-create
    STATUS      obsolete
    DESCRIPTION
        "The value of the object tBgpPrngPlcyImportPolicy2 specifies the import
         policy number 2 for this peer.

         An empty string indicates that no import policy is applied.

         This object was obsoleted in release 10.0. It is replaced by object
         tBgpPeeringPlcyImportPolicy2."
    DEFVAL      { ''H }
    ::= { tBgpPeeringPolicyEntry 20 }

tBgpPrngPlcyImportPolicy3        OBJECT-TYPE
    SYNTAX      TPolicyStatementNameOrEmpty
    MAX-ACCESS  read-create
    STATUS      obsolete
    DESCRIPTION
        "The value of the object tBgpPrngPlcyImportPolicy3 specifies the import
         policy number 3 for this peer.

         An empty string indicates that no import policy is applied.

         This object was obsoleted in release 10.0. It is replaced by object
         tBgpPeeringPlcyImportPolicy3."
    DEFVAL      { ''H }
    ::= { tBgpPeeringPolicyEntry 21 }

tBgpPrngPlcyImportPolicy4        OBJECT-TYPE
    SYNTAX      TPolicyStatementNameOrEmpty
    MAX-ACCESS  read-create
    STATUS      obsolete
    DESCRIPTION
        "The value of the object tBgpPrngPlcyImportPolicy4 specifies the import
         policy number 4 for this peer.

         An empty string indicates that no import policy is applied.

         This object was obsoleted in release 10.0. It is replaced by object
         tBgpPeeringPlcyImportPolicy4."
    DEFVAL      { ''H }
    ::= { tBgpPeeringPolicyEntry 22 }

tBgpPrngPlcyImportPolicy5        OBJECT-TYPE
    SYNTAX      TPolicyStatementNameOrEmpty
    MAX-ACCESS  read-create
    STATUS      obsolete
    DESCRIPTION
        "The value of the object tBgpPrngPlcyImportPolicy5 specifies the import
         policy number 5 for this peer.

         An empty string indicates that no import policy is applied.

         This object was obsoleted in release 10.0. It is replaced by object
         tBgpPeeringPlcyImportPolicy5."
    DEFVAL      { ''H }
    ::= { tBgpPeeringPolicyEntry 23 }

tBgpPrngPlcyExportPolicy1        OBJECT-TYPE
    SYNTAX      TPolicyStatementNameOrEmpty
    MAX-ACCESS  read-create
    STATUS      obsolete
    DESCRIPTION
        "The value of the object tBgpPrngPlcyExportPolicy1 specifies the export
         policy number 1 for this peer.

         An empty string indicates that no export policy is applied.

         This object was obsoleted in release 10.0. It is replaced by object
         tBgpPeeringPlcyExportPolicy1."
    DEFVAL      { ''H }
    ::= { tBgpPeeringPolicyEntry 24 }

tBgpPrngPlcyExportPolicy2        OBJECT-TYPE
    SYNTAX      TPolicyStatementNameOrEmpty
    MAX-ACCESS  read-create
    STATUS      obsolete
    DESCRIPTION
        "The value of the object tBgpPrngPlcyExportPolicy2 specifies the export
         policy number 2 for this peer.

         An empty string indicates that no export policy is applied.

         This object was obsoleted in release 10.0. It is replaced by object
         tBgpPeeringPlcyExportPolicy2."
    DEFVAL      { ''H }
    ::= { tBgpPeeringPolicyEntry 25 }

tBgpPrngPlcyExportPolicy3        OBJECT-TYPE
    SYNTAX      TPolicyStatementNameOrEmpty
    MAX-ACCESS  read-create
    STATUS      obsolete
    DESCRIPTION
        "The value of the object tBgpPrngPlcyExportPolicy3 specifies the export
         policy number 3 for this peer.

         An empty string indicates that no export policy is applied.

         This object was obsoleted in release 10.0. It is replaced by object
         tBgpPeeringPlcyExportPolicy3."
    DEFVAL      { ''H }
    ::= { tBgpPeeringPolicyEntry 26 }

tBgpPrngPlcyExportPolicy4        OBJECT-TYPE
    SYNTAX      TPolicyStatementNameOrEmpty
    MAX-ACCESS  read-create
    STATUS      obsolete
    DESCRIPTION
        "The value of the object tBgpPrngPlcyExportPolicy4 specifies the export
         policy number 4 for this peer.

         An empty string indicates that no export policy is applied.

         This object was obsoleted in release 10.0. It is replaced by object
         tBgpPeeringPlcyExportPolicy4."
    DEFVAL      { ''H }
    ::= { tBgpPeeringPolicyEntry 27 }

tBgpPrngPlcyExportPolicy5        OBJECT-TYPE
    SYNTAX      TPolicyStatementNameOrEmpty
    MAX-ACCESS  read-create
    STATUS      obsolete
    DESCRIPTION
        "The value of the object tBgpPrngPlcyExportPolicy5 specifies the export
         policy number 5 for this peer.

         An empty string indicates that no export policy is applied.

         This object was obsoleted in release 10.0. It is replaced by object
         tBgpPeeringPlcyExportPolicy5."
    DEFVAL      { ''H }
    ::= { tBgpPeeringPolicyEntry 28 }

tBgpPrngPlcyHoldTime             OBJECT-TYPE
    SYNTAX      BgpHoldTime
    UNITS       "seconds"
    MAX-ACCESS  read-create
    STATUS      current
    DESCRIPTION
        "The value of the object tBgpPrngPlcyHoldTime specifies the value (in
         seconds) of the BGP Hold Time Parameter."
    REFERENCE
        "BGP4-MIB.bgpPeerHoldTime"
    DEFVAL      { 90 }
    ::= { tBgpPeeringPolicyEntry 29 }

tBgpPrngPlcyKeepAlive            OBJECT-TYPE
    SYNTAX      BgpKeepAliveTime
    UNITS       "seconds"
    MAX-ACCESS  read-create
    STATUS      current
    DESCRIPTION
        "The value of the object tBgpPrngPlcyKeepAlive specifies
         the value of the BGP Keepalive timer.  A keepalive message
         is sent every time this timer expires."
    REFERENCE
        "BGP4-MIB.bgpPeerKeepAlive"
    DEFVAL      { 30 }
    ::= { tBgpPeeringPolicyEntry 30 }

tBgpPrngPlcyLocalAddressType     OBJECT-TYPE
    SYNTAX      InetAddressType
    MAX-ACCESS  read-create
    STATUS      current
    DESCRIPTION
        "The value of tBgpPrngPlcyLocalAddressType specifies the address type
         of the peer group local address."
    ::= { tBgpPeeringPolicyEntry 31 }

tBgpPrngPlcyLocalAddress         OBJECT-TYPE
    SYNTAX      InetAddress (SIZE (0|4|16))
    MAX-ACCESS  read-create
    STATUS      current
    DESCRIPTION
        "The value of tBgpPrngPlcyLocalAddress specifies the address of the
         peer group local address. The type of address contained in
         tBgpPrngPlcyLocalAddress is determined by
         tBgpPrngPlcyLocalAddressType.

         If local address is not set, tBgpPrngPlcyLocalAddressType is set to
         unknown and tBgpPrngPlcyLocalAddress returns a null string."
    ::= { tBgpPeeringPolicyEntry 32 }

tBgpPrngPlcyLocalAS              OBJECT-TYPE
    SYNTAX      InetAutonomousSystemNumber
    MAX-ACCESS  read-create
    STATUS      current
    DESCRIPTION
        "The value of the object tBgpPrngPlcyLocalAS specifies the autonomous
         system number to be advertised to this peer."
    DEFVAL      { 0 }
    ::= { tBgpPeeringPolicyEntry 33 }

tBgpPrngPlcyLocalASPrivate       OBJECT-TYPE
    SYNTAX      TruthValue
    MAX-ACCESS  read-create
    STATUS      current
    DESCRIPTION
        "If tBgpPrngPlcyLocalASPrivate is true, specifies that the local
         autonomous system number is hidden in paths learned from peering."
    DEFVAL      { false }
    ::= { tBgpPeeringPolicyEntry 34 }

tBgpPrngPlcyLocalPreference      OBJECT-TYPE
    SYNTAX      TmnxBgpLocalPreference
    MAX-ACCESS  read-create
    STATUS      current
    DESCRIPTION
        "The value of the object tBgpPrngPlcyLocalPreference specifies
         the default value for the Local Preference attribute.
         This value is used if the BGP route arrives from a BGP peer
         without the Local Pref attribute set.  It is overridden by
         any value set via a route policy."
    DEFVAL      { 100 }
    ::= { tBgpPeeringPolicyEntry 35 }

tBgpPrngPlcyLoopDetect           OBJECT-TYPE
    SYNTAX      BgpLoopDetect
    MAX-ACCESS  read-create
    STATUS      current
    DESCRIPTION
        "The value of the object tBgpPrngPlcyLoopDetect specifies how the peer
         session should deal with loop detection in the AS Path."
    DEFVAL      { ignore }
    ::= { tBgpPeeringPolicyEntry 36 }

tBgpPrngPlcyMEDSource            OBJECT-TYPE
    SYNTAX      BgpMEDSource
    MAX-ACCESS  read-create
    STATUS      current
    DESCRIPTION
        "The value of tBgpPrngPlcyMEDSource specifies the Multi Exit
         Discriminator value source for this peer."
    DEFVAL      { noMedOut }
    ::= { tBgpPeeringPolicyEntry 37 }

tBgpPrngPlcyMEDValue             OBJECT-TYPE
    SYNTAX      BgpMEDValue
    MAX-ACCESS  read-create
    STATUS      current
    DESCRIPTION
        "The value of the object tBgpPrngPlcyMEDValue specifies,when
         tBgpPeerMEDSource is metricVal, the Multi Exit Discriminator value for
         this peer. Otherwise the value of this object is ignored."
    DEFVAL      { 0 }
    ::= { tBgpPeeringPolicyEntry 38 }

tBgpPrngPlcyMinASOrigination     OBJECT-TYPE
    SYNTAX      BgpMinASOriginationTime
    UNITS       "seconds"
    MAX-ACCESS  read-create
    STATUS      obsolete
    DESCRIPTION
        "The value of the object tBgpPrngPlcyMinASOrigination specifies the
         minimal interval (in seconds) at which a given path attribute can be
         advertised to a peer."
    REFERENCE
        "BGP4-MIB.bgpPeerMinASOriginationInterval"
    DEFVAL      { 15 }
    ::= { tBgpPeeringPolicyEntry 39 }

tBgpPrngPlcyMinRteAdvertisement  OBJECT-TYPE
    SYNTAX      BgpMinRouteAdvertisement
    UNITS       "seconds"
    MAX-ACCESS  read-create
    STATUS      current
    DESCRIPTION
        "The value of the object tBgpPrngPlcyMinRteAdvertisement specifies the
         minimum interval at which a given path attribute can be advertised to
         a peer."
    DEFVAL      { 30 }
    ::= { tBgpPeeringPolicyEntry 40 }

tBgpPrngPlcyMultihop             OBJECT-TYPE
    SYNTAX      BgpTimeToLive
    UNITS       "TTL hops"
    MAX-ACCESS  read-create
    STATUS      current
    DESCRIPTION
        "The value of the object tBgpPrngPlcyMultihop specifies the TTL used in
         IP packet header for BGP advertisements. Default TTL values for EBGP
         peer is 1, and MAX_TTL for IBGP peers. Default value if not set is
         no_type - the peer has to infer its value based on local-as, and
         peer-as in that case."
    DEFVAL      { 0 }
    ::= { tBgpPeeringPolicyEntry 41 }

tBgpPrngPlcyNextHopSelf          OBJECT-TYPE
    SYNTAX      TruthValue
    MAX-ACCESS  read-create
    STATUS      current
    DESCRIPTION
        "The value of the object tBgpPrngPlcyNextHopSelf specifies whether or
         not routes advertised to EBGP peers have NEXTHOP path attribute set to
         this router's physical interface. When false, third party routes are
         advertised."
    DEFVAL      { false }
    ::= { tBgpPeeringPolicyEntry 42 }

tBgpPrngPlcyPassive              OBJECT-TYPE
    SYNTAX      TruthValue
    MAX-ACCESS  read-create
    STATUS      current
    DESCRIPTION
        "The value of the object tBgpPrngPlcyPassive specifies whether or not
         this router will attempt to connect to the peer, or will wait for the
         peer to connect. If set to true, this router will NOT attempt to
         connect to the peer, but will wait passively for the peer to connect."
    DEFVAL      { false }
    ::= { tBgpPeeringPolicyEntry 43 }

tBgpPrngPlcyPeerAS               OBJECT-TYPE
    SYNTAX      InetAutonomousSystemNumber
    MAX-ACCESS  read-create
    STATUS      current
    DESCRIPTION
        "The value of the object tBgpPrngPlcyPeerAS specifies the Autonomous
         System number for the remote peer."
    DEFVAL      { 0 }
    ::= { tBgpPeeringPolicyEntry 44 }

tBgpPrngPlcyPreference           OBJECT-TYPE
    SYNTAX      TmnxBgpPreference (1..255)
    MAX-ACCESS  read-create
    STATUS      current
    DESCRIPTION
        "The value of the object tBgpPrngPlcyPreference  specifies
         the route preference for routes learned via the peer."
    DEFVAL      { 170 }
    ::= { tBgpPeeringPolicyEntry 45 }

tBgpPrngPlcyMaxPrefix            OBJECT-TYPE
    SYNTAX      BgpPrefixLimit
    UNITS       "number of routes"
    MAX-ACCESS  read-create
    STATUS      current
    DESCRIPTION
        "The value of tBgpPrngPlcyMaxPrefix is ignored. This object will be
         obsoleted in a future release."
    DEFVAL      { 0 }
    ::= { tBgpPeeringPolicyEntry 46 }

tBgpPrngPlcyRemovePrivateAS      OBJECT-TYPE
    SYNTAX      TruthValue
    MAX-ACCESS  read-create
    STATUS      current
    DESCRIPTION
        "The value of the object tBgpPrngPlcyRemovePrivateAS specifies whether
         or not private AS numbers should be stripped from the AS Path before
         advertising them to BGP peers."
    DEFVAL      { false }
    ::= { tBgpPeeringPolicyEntry 47 }

tBgpPrngPlcyMinTTLValue          OBJECT-TYPE
    SYNTAX      Unsigned32 (0 | 1..255)
    MAX-ACCESS  read-create
    STATUS      current
    DESCRIPTION
        "The value of tBgpPrngPlcyMinTTLValue specifies the minimum TTL value
         for an incoming BGP packet.

         If tBgpPrngPlcyMinTTLValue is set to zero (0), the TTL Security
         feature is disabled."
    DEFVAL      { 0 }
    ::= { tBgpPeeringPolicyEntry 48 }

tBgpPrngPlcyPeerType             OBJECT-TYPE
    SYNTAX      BgpPeerType
    MAX-ACCESS  read-create
    STATUS      current
    DESCRIPTION
        "The value of the object tBgpPrngPlcyPeerType specifies the type of
         peer - noType(1), internal(2) and external(3). Default value if not
         set is noType - the peer has to infer its value based on local-as, and
         peer-as in that case."
    DEFVAL      { noType }
    ::= { tBgpPeeringPolicyEntry 49 }

tBgpPrngPlcyDisable4ByteASN      OBJECT-TYPE
    SYNTAX      TruthValue
    MAX-ACCESS  read-create
    STATUS      current
    DESCRIPTION
        "The value of tBgpPrngPlcyDisable4ByteASN specifies whether or not
         4-byte ASN capability will be advertised by this peer.

         When the value of tBgpPrngPlcyDisable4ByteASN is set to false, 4-byte
         ASN support will be negotiated with the associated remote peers. When
         the value of tBgpPrngPlcyDisable4ByteASN is set to true, 4-byte ASN
         capability will not be advertised by this peer."
    DEFVAL      { false }
    ::= { tBgpPeeringPolicyEntry 50 }

tBgpPrngPlcyRemovePrivateASLmtd  OBJECT-TYPE
    SYNTAX      TruthValue
    MAX-ACCESS  read-create
    STATUS      current
    DESCRIPTION
        "The value of tBgpPrngPlcyRemovePrivateASLmtd specifies whether this
         BGP peer will remove the private AS numbers.

         When the value of tBgpPeerNgRemovePrivateASLmtd is true, this BGP peer
         will remove private AS numbers from the AS Path."
    DEFVAL      { false }
    ::= { tBgpPeeringPolicyEntry 51 }

tBgpPrngPlcyMaxPrefixLogOnly     OBJECT-TYPE
    SYNTAX      TruthValue
    MAX-ACCESS  read-create
    STATUS      current
    DESCRIPTION
        "The value of tBgpPrngPlcyMaxPrefixLogOnly specifies whether BGP
         peering will be disabled when tBgpPrngPlcyMaxPrefix is exceeded.

         When the value is set to 'true', BGP peering will be enabled.

         When the value is set to 'false', BGP peering will be disabled. This
         object will be obsoleted in a future release."
    DEFVAL      { false }
    ::= { tBgpPeeringPolicyEntry 52 }

tBgpPrngPlcyMaxPrefixThreshold   OBJECT-TYPE
    SYNTAX      Unsigned32 (1..100)
    UNITS       "percent"
    MAX-ACCESS  read-create
    STATUS      current
    DESCRIPTION
        "The value of tBgpPrngPlcyMaxPrefixThreshold specifies a percentage of
         tBgpPrngPlcyMaxPrefix. This object will be obsoleted in a future
         release."
    DEFVAL      { 90 }
    ::= { tBgpPeeringPolicyEntry 53 }

tBgpPrngPlcyBfdEnable            OBJECT-TYPE
    SYNTAX      TruthValue
    MAX-ACCESS  read-create
    STATUS      current
    DESCRIPTION
        "The value of tBgpPrngPlcyBfdEnable specifies whether or not a BFD
         session to track the dynamic BGP peer is established for all BGP peers
         that are setup using this policy."
    DEFVAL      { false }
    ::= { tBgpPeeringPolicyEntry 54 }

tBgpPrngPlcyFamilyIpv4           OBJECT-TYPE
    SYNTAX      TruthValue
    MAX-ACCESS  read-create
    STATUS      current
    DESCRIPTION
        "The value of the object tBgpPrngPlcyFamilyIpv4 specifies if IPv4
         routes can be exchanged.

         If the value of this object and the value of 'tBgpPrngPlcyFamilyIpv6'
         are both equal to 'false', the system exchanges only IPv4 routes with
         IPv4 peers."
    DEFVAL      { false }
    ::= { tBgpPeeringPolicyEntry 55 }

tBgpPrngPlcyFamilyIpv6           OBJECT-TYPE
    SYNTAX      TruthValue
    MAX-ACCESS  read-create
    STATUS      current
    DESCRIPTION
        "The value of the object tBgpPrngPlcyFamilyIpv6 specifies if IPv6
         routes can be exchanged.

         If the value of this object and the value of 'tBgpPrngPlcyFamilyIpv4'
         are both equal to 'false', the system exchanges only IPv6 routes with
         IPv6 peers."
    DEFVAL      { false }
    ::= { tBgpPeeringPolicyEntry 56 }

tBgpPeeringPlcyTable             OBJECT-TYPE
    SYNTAX      SEQUENCE OF TBgpPeeringPlcyEntry
    MAX-ACCESS  not-accessible
    STATUS      current
    DESCRIPTION
        "The tBgpPeeringPlcyTable contains BGP peering policies."
    ::= { tBgpPeeringPolicyObjects 3 }

tBgpPeeringPlcyEntry             OBJECT-TYPE
    SYNTAX      TBgpPeeringPlcyEntry
    MAX-ACCESS  not-accessible
    STATUS      current
    DESCRIPTION
        "An entry (conceptual row) in the tBgpPeeringPlcyTable."
    AUGMENTS    { tBgpPeeringPolicyEntry }
    ::= { tBgpPeeringPlcyTable 1 }

TBgpPeeringPlcyEntry             ::= SEQUENCE
{
    tBgpPeeringPlcyImportPolicy1     TPolicyStatementNameOrEmpty,
    tBgpPeeringPlcyImportPolicy2     TPolicyStatementNameOrEmpty,
    tBgpPeeringPlcyImportPolicy3     TPolicyStatementNameOrEmpty,
    tBgpPeeringPlcyImportPolicy4     TPolicyStatementNameOrEmpty,
    tBgpPeeringPlcyImportPolicy5     TPolicyStatementNameOrEmpty,
    tBgpPeeringPlcyImportPolicy6     TPolicyStatementNameOrEmpty,
    tBgpPeeringPlcyImportPolicy7     TPolicyStatementNameOrEmpty,
    tBgpPeeringPlcyImportPolicy8     TPolicyStatementNameOrEmpty,
    tBgpPeeringPlcyImportPolicy9     TPolicyStatementNameOrEmpty,
    tBgpPeeringPlcyImportPolicy10    TPolicyStatementNameOrEmpty,
    tBgpPeeringPlcyImportPolicy11    TPolicyStatementNameOrEmpty,
    tBgpPeeringPlcyImportPolicy12    TPolicyStatementNameOrEmpty,
    tBgpPeeringPlcyImportPolicy13    TPolicyStatementNameOrEmpty,
    tBgpPeeringPlcyImportPolicy14    TPolicyStatementNameOrEmpty,
    tBgpPeeringPlcyImportPolicy15    TPolicyStatementNameOrEmpty,
    tBgpPeeringPlcyExportPolicy1     TPolicyStatementNameOrEmpty,
    tBgpPeeringPlcyExportPolicy2     TPolicyStatementNameOrEmpty,
    tBgpPeeringPlcyExportPolicy3     TPolicyStatementNameOrEmpty,
    tBgpPeeringPlcyExportPolicy4     TPolicyStatementNameOrEmpty,
    tBgpPeeringPlcyExportPolicy5     TPolicyStatementNameOrEmpty,
    tBgpPeeringPlcyExportPolicy6     TPolicyStatementNameOrEmpty,
    tBgpPeeringPlcyExportPolicy7     TPolicyStatementNameOrEmpty,
    tBgpPeeringPlcyExportPolicy8     TPolicyStatementNameOrEmpty,
    tBgpPeeringPlcyExportPolicy9     TPolicyStatementNameOrEmpty,
    tBgpPeeringPlcyExportPolicy10    TPolicyStatementNameOrEmpty,
    tBgpPeeringPlcyExportPolicy11    TPolicyStatementNameOrEmpty,
    tBgpPeeringPlcyExportPolicy12    TPolicyStatementNameOrEmpty,
    tBgpPeeringPlcyExportPolicy13    TPolicyStatementNameOrEmpty,
    tBgpPeeringPlcyExportPolicy14    TPolicyStatementNameOrEmpty,
    tBgpPeeringPlcyExportPolicy15    TPolicyStatementNameOrEmpty
}

tBgpPeeringPlcyImportPolicy1     OBJECT-TYPE
    SYNTAX      TPolicyStatementNameOrEmpty
    MAX-ACCESS  read-create
    STATUS      current
    DESCRIPTION
        "The value of tBgpPeeringPlcyImportPolicy1 specifies the first import
         policy."
    DEFVAL      { ''H }
    ::= { tBgpPeeringPlcyEntry 1 }

tBgpPeeringPlcyImportPolicy2     OBJECT-TYPE
    SYNTAX      TPolicyStatementNameOrEmpty
    MAX-ACCESS  read-create
    STATUS      current
    DESCRIPTION
        "The value of tBgpPeeringPlcyImportPolicy2 specifies the second import
         policy."
    DEFVAL      { ''H }
    ::= { tBgpPeeringPlcyEntry 2 }

tBgpPeeringPlcyImportPolicy3     OBJECT-TYPE
    SYNTAX      TPolicyStatementNameOrEmpty
    MAX-ACCESS  read-create
    STATUS      current
    DESCRIPTION
        "The value of tBgpPeeringPlcyImportPolicy3 specifies the third import
         policy."
    DEFVAL      { ''H }
    ::= { tBgpPeeringPlcyEntry 3 }

tBgpPeeringPlcyImportPolicy4     OBJECT-TYPE
    SYNTAX      TPolicyStatementNameOrEmpty
    MAX-ACCESS  read-create
    STATUS      current
    DESCRIPTION
        "The value of tBgpPeeringPlcyImportPolicy4 specifies the fourth import
         policy."
    DEFVAL      { ''H }
    ::= { tBgpPeeringPlcyEntry 4 }

tBgpPeeringPlcyImportPolicy5     OBJECT-TYPE
    SYNTAX      TPolicyStatementNameOrEmpty
    MAX-ACCESS  read-create
    STATUS      current
    DESCRIPTION
        "The value of tBgpPeeringPlcyImportPolicy5 specifies the fifth import
         policy."
    DEFVAL      { ''H }
    ::= { tBgpPeeringPlcyEntry 5 }

tBgpPeeringPlcyImportPolicy6     OBJECT-TYPE
    SYNTAX      TPolicyStatementNameOrEmpty
    MAX-ACCESS  read-create
    STATUS      current
    DESCRIPTION
        "The value of tBgpPeeringPlcyImportPolicy6 specifies the sixth import
         policy."
    DEFVAL      { ''H }
    ::= { tBgpPeeringPlcyEntry 6 }

tBgpPeeringPlcyImportPolicy7     OBJECT-TYPE
    SYNTAX      TPolicyStatementNameOrEmpty
    MAX-ACCESS  read-create
    STATUS      current
    DESCRIPTION
        "The value of tBgpPeeringPlcyImportPolicy7 specifies the seventh import
         policy."
    DEFVAL      { ''H }
    ::= { tBgpPeeringPlcyEntry 7 }

tBgpPeeringPlcyImportPolicy8     OBJECT-TYPE
    SYNTAX      TPolicyStatementNameOrEmpty
    MAX-ACCESS  read-create
    STATUS      current
    DESCRIPTION
        "The value of tBgpPeeringPlcyImportPolicy8 specifies the eighth import
         policy."
    DEFVAL      { ''H }
    ::= { tBgpPeeringPlcyEntry 8 }

tBgpPeeringPlcyImportPolicy9     OBJECT-TYPE
    SYNTAX      TPolicyStatementNameOrEmpty
    MAX-ACCESS  read-create
    STATUS      current
    DESCRIPTION
        "The value of tBgpPeeringPlcyImportPolicy9 specifies the ninth import
         policy."
    DEFVAL      { ''H }
    ::= { tBgpPeeringPlcyEntry 9 }

tBgpPeeringPlcyImportPolicy10    OBJECT-TYPE
    SYNTAX      TPolicyStatementNameOrEmpty
    MAX-ACCESS  read-create
    STATUS      current
    DESCRIPTION
        "The value of tBgpPeeringPlcyImportPolicy10 specifies the tenth import
         policy."
    DEFVAL      { ''H }
    ::= { tBgpPeeringPlcyEntry 10 }

tBgpPeeringPlcyImportPolicy11    OBJECT-TYPE
    SYNTAX      TPolicyStatementNameOrEmpty
    MAX-ACCESS  read-create
    STATUS      current
    DESCRIPTION
        "The value of tBgpPeeringPlcyImportPolicy11 specifies the eleventh
         import policy."
    DEFVAL      { ''H }
    ::= { tBgpPeeringPlcyEntry 11 }

tBgpPeeringPlcyImportPolicy12    OBJECT-TYPE
    SYNTAX      TPolicyStatementNameOrEmpty
    MAX-ACCESS  read-create
    STATUS      current
    DESCRIPTION
        "The value of tBgpPeeringPlcyImportPolicy12 specifies the twelfth
         import policy."
    DEFVAL      { ''H }
    ::= { tBgpPeeringPlcyEntry 12 }

tBgpPeeringPlcyImportPolicy13    OBJECT-TYPE
    SYNTAX      TPolicyStatementNameOrEmpty
    MAX-ACCESS  read-create
    STATUS      current
    DESCRIPTION
        "The value of tBgpPeeringPlcyImportPolicy13 specifies the thirteenth
         import policy."
    DEFVAL      { ''H }
    ::= { tBgpPeeringPlcyEntry 13 }

tBgpPeeringPlcyImportPolicy14    OBJECT-TYPE
    SYNTAX      TPolicyStatementNameOrEmpty
    MAX-ACCESS  read-create
    STATUS      current
    DESCRIPTION
        "The value of tBgpPeeringPlcyImportPolicy14 specifies the fourteenth
         import policy."
    DEFVAL      { ''H }
    ::= { tBgpPeeringPlcyEntry 14 }

tBgpPeeringPlcyImportPolicy15    OBJECT-TYPE
    SYNTAX      TPolicyStatementNameOrEmpty
    MAX-ACCESS  read-create
    STATUS      current
    DESCRIPTION
        "The value of tBgpPeeringPlcyImportPolicy15 specifies the fifteenth
         import policy."
    DEFVAL      { ''H }
    ::= { tBgpPeeringPlcyEntry 15 }

tBgpPeeringPlcyExportPolicy1     OBJECT-TYPE
    SYNTAX      TPolicyStatementNameOrEmpty
    MAX-ACCESS  read-create
    STATUS      current
    DESCRIPTION
        "The value of tBgpPeeringPlcyExportPolicy1 specifies the first export
         policy."
    DEFVAL      { ''H }
    ::= { tBgpPeeringPlcyEntry 16 }

tBgpPeeringPlcyExportPolicy2     OBJECT-TYPE
    SYNTAX      TPolicyStatementNameOrEmpty
    MAX-ACCESS  read-create
    STATUS      current
    DESCRIPTION
        "The value of tBgpPeeringPlcyExportPolicy2 specifies the second export
         policy."
    DEFVAL      { ''H }
    ::= { tBgpPeeringPlcyEntry 17 }

tBgpPeeringPlcyExportPolicy3     OBJECT-TYPE
    SYNTAX      TPolicyStatementNameOrEmpty
    MAX-ACCESS  read-create
    STATUS      current
    DESCRIPTION
        "The value of tBgpPeeringPlcyExportPolicy3 specifies the third export
         policy."
    DEFVAL      { ''H }
    ::= { tBgpPeeringPlcyEntry 18 }

tBgpPeeringPlcyExportPolicy4     OBJECT-TYPE
    SYNTAX      TPolicyStatementNameOrEmpty
    MAX-ACCESS  read-create
    STATUS      current
    DESCRIPTION
        "The value of tBgpPeeringPlcyExportPolicy4 specifies the fourth export
         policy."
    DEFVAL      { ''H }
    ::= { tBgpPeeringPlcyEntry 19 }

tBgpPeeringPlcyExportPolicy5     OBJECT-TYPE
    SYNTAX      TPolicyStatementNameOrEmpty
    MAX-ACCESS  read-create
    STATUS      current
    DESCRIPTION
        "The value of tBgpPeeringPlcyExportPolicy5 specifies the fifth export
         policy."
    DEFVAL      { ''H }
    ::= { tBgpPeeringPlcyEntry 20 }

tBgpPeeringPlcyExportPolicy6     OBJECT-TYPE
    SYNTAX      TPolicyStatementNameOrEmpty
    MAX-ACCESS  read-create
    STATUS      current
    DESCRIPTION
        "The value of tBgpPeeringPlcyExportPolicy6 specifies the sixth export
         policy."
    DEFVAL      { ''H }
    ::= { tBgpPeeringPlcyEntry 21 }

tBgpPeeringPlcyExportPolicy7     OBJECT-TYPE
    SYNTAX      TPolicyStatementNameOrEmpty
    MAX-ACCESS  read-create
    STATUS      current
    DESCRIPTION
        "The value of tBgpPeeringPlcyExportPolicy7 specifies the seventh export
         policy."
    DEFVAL      { ''H }
    ::= { tBgpPeeringPlcyEntry 22 }

tBgpPeeringPlcyExportPolicy8     OBJECT-TYPE
    SYNTAX      TPolicyStatementNameOrEmpty
    MAX-ACCESS  read-create
    STATUS      current
    DESCRIPTION
        "The value of tBgpPeeringPlcyExportPolicy8 specifies the eighth export
         policy."
    DEFVAL      { ''H }
    ::= { tBgpPeeringPlcyEntry 23 }

tBgpPeeringPlcyExportPolicy9     OBJECT-TYPE
    SYNTAX      TPolicyStatementNameOrEmpty
    MAX-ACCESS  read-create
    STATUS      current
    DESCRIPTION
        "The value of tBgpPeeringPlcyExportPolicy9 specifies the ninth export
         policy."
    DEFVAL      { ''H }
    ::= { tBgpPeeringPlcyEntry 24 }

tBgpPeeringPlcyExportPolicy10    OBJECT-TYPE
    SYNTAX      TPolicyStatementNameOrEmpty
    MAX-ACCESS  read-create
    STATUS      current
    DESCRIPTION
        "The value of tBgpPeeringPlcyExportPolicy10 specifies the tenth export
         policy."
    DEFVAL      { ''H }
    ::= { tBgpPeeringPlcyEntry 25 }

tBgpPeeringPlcyExportPolicy11    OBJECT-TYPE
    SYNTAX      TPolicyStatementNameOrEmpty
    MAX-ACCESS  read-create
    STATUS      current
    DESCRIPTION
        "The value of tBgpPeeringPlcyExportPolicy11 specifies the eleventh
         export policy."
    DEFVAL      { ''H }
    ::= { tBgpPeeringPlcyEntry 26 }

tBgpPeeringPlcyExportPolicy12    OBJECT-TYPE
    SYNTAX      TPolicyStatementNameOrEmpty
    MAX-ACCESS  read-create
    STATUS      current
    DESCRIPTION
        "The value of tBgpPeeringPlcyExportPolicy12 specifies the twelfth
         export policy."
    DEFVAL      { ''H }
    ::= { tBgpPeeringPlcyEntry 27 }

tBgpPeeringPlcyExportPolicy13    OBJECT-TYPE
    SYNTAX      TPolicyStatementNameOrEmpty
    MAX-ACCESS  read-create
    STATUS      current
    DESCRIPTION
        "The value of tBgpPeeringPlcyExportPolicy13 specifies the thirteenth
         export policy."
    DEFVAL      { ''H }
    ::= { tBgpPeeringPlcyEntry 28 }

tBgpPeeringPlcyExportPolicy14    OBJECT-TYPE
    SYNTAX      TPolicyStatementNameOrEmpty
    MAX-ACCESS  read-create
    STATUS      current
    DESCRIPTION
        "The value of tBgpPeeringPlcyExportPolicy14 specifies the fourteenth
         export policy."
    DEFVAL      { ''H }
    ::= { tBgpPeeringPlcyEntry 29 }

tBgpPeeringPlcyExportPolicy15    OBJECT-TYPE
    SYNTAX      TPolicyStatementNameOrEmpty
    MAX-ACCESS  read-create
    STATUS      current
    DESCRIPTION
        "The value of tBgpPeeringPlcyExportPolicy15 specifies the fifteenth
         export policy."
    DEFVAL      { ''H }
    ::= { tBgpPeeringPlcyEntry 30 }

tBgpPrngPlcyPfxLmtTableLastChngd OBJECT-TYPE
    SYNTAX      TimeStamp
    MAX-ACCESS  read-only
    STATUS      current
    DESCRIPTION
        "The value of tBgpPrngPlcyPfxLmtTableLastChngd indicates the sysUpTime
         when any type of change was last made to the tBgpPrngPlcyPfxLmtTable."
    ::= { tBgpPeeringPolicyObjects 4 }

tBgpPrngPlcyPfxLmtTable          OBJECT-TYPE
    SYNTAX      SEQUENCE OF TBgpPrngPlcyPfxLmtEntry
    MAX-ACCESS  not-accessible
    STATUS      current
    DESCRIPTION
        "The tBgpPrngPlcyPfxLmtTable is the list of configured prefix limits
         per BGP peering policy and IP family."
    ::= { tBgpPeeringPolicyObjects 5 }

tBgpPrngPlcyPfxLmtEntry          OBJECT-TYPE
    SYNTAX      TBgpPrngPlcyPfxLmtEntry
    MAX-ACCESS  not-accessible
    STATUS      current
    DESCRIPTION
        "An entry (conceptual row) in the tBgpPrngPlcyPfxLmtTable.

         An entry can be created and removed using the row status object,
         tBgpPrngPlcyPfxLmtRowStatus."
    INDEX       {
        tBgpPeeringPolicyName,
        tBgpPrngPlcyPfxLmtFamily
    }
    ::= { tBgpPrngPlcyPfxLmtTable 1 }

TBgpPrngPlcyPfxLmtEntry          ::= SEQUENCE
{
    tBgpPrngPlcyPfxLmtFamily         INTEGER,
    tBgpPrngPlcyPfxLmtLastChanged    TimeStamp,
    tBgpPrngPlcyPfxLmtRowStatus      RowStatus,
    tBgpPrngPlcyPfxLmtMaxPrefix      BgpPrefixLimit,
    tBgpPrngPlcyPfxLmtLogOnly        TruthValue,
    tBgpPrngPlcyPfxLmtThreshold      Unsigned32,
    tBgpPrngPlcyPfxLmtIdleTimeOut    Integer32,
    tBgpPrngPlcyPfxLmtPostImport     TruthValue
}

tBgpPrngPlcyPfxLmtFamily         OBJECT-TYPE
    SYNTAX      INTEGER {
        ipv4 (1),
        ipv6 (2)
    }
    MAX-ACCESS  not-accessible
    STATUS      current
    DESCRIPTION
        "The value of tBgpPrngPlcyPfxLmtFamily specifies the address family for
         which prefix-limit is configured."
    ::= { tBgpPrngPlcyPfxLmtEntry 1 }

tBgpPrngPlcyPfxLmtLastChanged    OBJECT-TYPE
    SYNTAX      TimeStamp
    MAX-ACCESS  read-only
    STATUS      current
    DESCRIPTION
        "The value tBgpPrngPlcyPfxLmtLastChanged indicates when an entry in
         tBgpPrngPlcyPfxLmtTable was last changed."
    ::= { tBgpPrngPlcyPfxLmtEntry 2 }

tBgpPrngPlcyPfxLmtRowStatus      OBJECT-TYPE
    SYNTAX      RowStatus
    MAX-ACCESS  read-create
    STATUS      current
    DESCRIPTION
        "The value of tBgpPrngPlcyPfxLmtRowStatus specifies the row status for
         this BGP instance for the virtual router. It is used to create and
         delete row entries in this table."
    ::= { tBgpPrngPlcyPfxLmtEntry 3 }

tBgpPrngPlcyPfxLmtMaxPrefix      OBJECT-TYPE
    SYNTAX      BgpPrefixLimit
    MAX-ACCESS  read-create
    STATUS      current
    DESCRIPTION
        "The value of tBgpPrngPlcyPfxLmtMaxPrefix specifies the maximum number
         of routes that can be learned from this peer.

         A value of zero is not allowed. A value for this object must be
         specified when the row is created."
    ::= { tBgpPrngPlcyPfxLmtEntry 4 }

tBgpPrngPlcyPfxLmtLogOnly        OBJECT-TYPE
    SYNTAX      TruthValue
    MAX-ACCESS  read-create
    STATUS      current
    DESCRIPTION
        "The value of tBgpPrngPlcyPfxLmtLogOnly specifies whether BGP peering
         will be disabled when tBgpPrngPlcyPfxLmtMaxPrefix is exceeded.

         When the value is set to 'true', BGP peering will remain enabled.

         When the value is set to 'false', BGP peering will be disabled."
    DEFVAL      { false }
    ::= { tBgpPrngPlcyPfxLmtEntry 5 }

tBgpPrngPlcyPfxLmtThreshold      OBJECT-TYPE
    SYNTAX      Unsigned32 (1..100)
    UNITS       "percent"
    MAX-ACCESS  read-create
    STATUS      current
    DESCRIPTION
        "The value of tBgpPrngPlcyPfxLmtThreshold specifies a percentage of
         tBgpPrngPlcyPfxLmtMaxPrefix."
    DEFVAL      { 90 }
    ::= { tBgpPrngPlcyPfxLmtEntry 6 }

tBgpPrngPlcyPfxLmtIdleTimeOut    OBJECT-TYPE
    SYNTAX      Integer32 (0..1024)
    UNITS       "minutes"
    MAX-ACCESS  read-create
    STATUS      current
    DESCRIPTION
        "The value of tBgpPrngPlcyPfxLmtIdleTimeOut specifies the idle time in
         minutes that the BGP peering remains disabled before attempting to
         automatically re-establish the connection with the peers in this BGP
         group after tBgpPrngPlcyPfxLmtMaxPrefix limit is reached.

         The default value of tBgpPrngPlcyPfxLmtIdleTimeOut is zero which
         means, no attempt will be made to re-establish the BGP peering with
         peers in this BGP group after tBgpPrngPlcyPfxLmtMaxPrefix limit is
         reached.

         When the value of tBgpPrngPlcyPfxLmtMaxPrefix is changed, the value of
         tBgpPrngPlcyPfxLmtIdleTimeOut is reset to its default value.

         An 'inconsistentValue' error is returned if an attempt is made to set
         this object to a non-default value when the value of
         tBgpPrngPlcyPfxLmtLogOnly is set to non-default value."
    DEFVAL      { 0 }
    ::= { tBgpPrngPlcyPfxLmtEntry 7 }

tBgpPrngPlcyPfxLmtPostImport     OBJECT-TYPE
    SYNTAX      TruthValue
    MAX-ACCESS  read-create
    STATUS      current
    DESCRIPTION
        "The value of tBgpPrngPlcyPfxLmtPostImport specifies that a route
         rejected by a BGP import policy should not be counted against the
         configured tBgpPrngPlcyPfxLmtMaxPrefix limit.

         When the value is set to 'true', it specifies that the limit should be
         enforced after import policies."
    DEFVAL      { false }
    ::= { tBgpPrngPlcyPfxLmtEntry 8 }

tBgpNotificationObjs             OBJECT IDENTIFIER ::= { tBgpObjects 7 }

tBgpPeerNgAddrType               OBJECT-TYPE
    SYNTAX      InetAddressType
    MAX-ACCESS  accessible-for-notify
    STATUS      current
    DESCRIPTION
        "The value of tBgpPeerNgAddrType indicates the type of address for the
         BGP peer represented by tBgpPeerNgAddr."
    ::= { tBgpNotificationObjs 1 }

tBgpPeerNgAddr                   OBJECT-TYPE
    SYNTAX      InetAddress
    MAX-ACCESS  accessible-for-notify
    STATUS      current
    DESCRIPTION
        "The value of tBgpPeerNgAddr indicates the address for the BGP peer."
    ::= { tBgpNotificationObjs 2 }

tBgpFlowspecExtCommunityAction   OBJECT-TYPE
    SYNTAX      TmnxBgpFlowRouteExtCommAction
    MAX-ACCESS  accessible-for-notify
    STATUS      current
    DESCRIPTION
        "The value of tBgpFlowspecExtCommunityAction indicates the extended
         community action received as part of flow route from a remote BGP
         peer."
    ::= { tBgpNotificationObjs 3 }

tBgpPeerFlowRouteDestAddrType    OBJECT-TYPE
    SYNTAX      InetAddressType
    MAX-ACCESS  accessible-for-notify
    STATUS      obsolete
    DESCRIPTION
        "The value of tBgpPeerFlowRouteDestAddrType indicates the type of
         address for the BGP peer represented by tBgpPeerFlowRouteDestAddr."
    ::= { tBgpNotificationObjs 4 }

tBgpPeerFlowRouteDestAddr        OBJECT-TYPE
    SYNTAX      InetAddress
    MAX-ACCESS  accessible-for-notify
    STATUS      obsolete
    DESCRIPTION
        "The value of tBgpPeerFlowRouteDestAddr indicates the address of the
         destination BGP peer received as part of a flow route."
    ::= { tBgpNotificationObjs 5 }

tBgpFlowRouteInvalidReason       OBJECT-TYPE
    SYNTAX      DisplayString
    MAX-ACCESS  accessible-for-notify
    STATUS      obsolete
    DESCRIPTION
        "The value of tBgpFlowRouteInvalidReason indicates the reason why the
         received flow route is invalid."
    DEFVAL      { ''H }
    ::= { tBgpNotificationObjs 6 }

tBgpFlowRouteNLRI                OBJECT-TYPE
    SYNTAX      OCTET STRING (SIZE (0..30))
    MAX-ACCESS  accessible-for-notify
    STATUS      obsolete
    DESCRIPTION
        "The value of tBgpFlowRouteNLRI contains at most the first 30 octets of
         the NLRI (Network Layer Reachability Information) received in a flow
         route."
    ::= { tBgpNotificationObjs 7 }

tBgpFlowspecExtCommActionValue   OBJECT-TYPE
    SYNTAX      OCTET STRING (SIZE (0..64))
    MAX-ACCESS  accessible-for-notify
    STATUS      current
    DESCRIPTION
        "The value of tBgpFlowspecExtCommActionValue indicates the extended
         community action value received as part of flow route from a remote
         BGP peer."
    ::= { tBgpNotificationObjs 8 }

tBgp4OptTransPathAttrType        OBJECT-TYPE
    SYNTAX      Integer32
    MAX-ACCESS  accessible-for-notify
    STATUS      obsolete
    DESCRIPTION
        "The value of tBgp4OptTransPathAttrType indicates the
         optional-transitive path attribute type received from a remote BGP
         peer.

         This object was obsoleted in R11.0 and replaced with
         tBgp4PathAttrType."
    ::= { tBgpNotificationObjs 9 }

tBgp4OptTransPathAttrLength      OBJECT-TYPE
    SYNTAX      Unsigned32
    MAX-ACCESS  accessible-for-notify
    STATUS      obsolete
    DESCRIPTION
        "The value of tBgp4OptTransPathAttrLength indicates the length of
         optional-transitive path attribute length received from a remote BGP
         peer.

         This object was obsoleted in R11.0 and replaced with
         tBgp4PathAttrLength."
    ::= { tBgpNotificationObjs 10 }

tBgp4OptTransPathAttribute       OBJECT-TYPE
    SYNTAX      OCTET STRING (SIZE (0..60))
    MAX-ACCESS  accessible-for-notify
    STATUS      obsolete
    DESCRIPTION
        "The value of tBgp4OptTransPathAttribute indicates the
         optional-transitive path attribute value received from a remote BGP
         peer.

         This object was obsoleted in R11.0 and replaced with
         tBgp4PathAttribute."
    ::= { tBgpNotificationObjs 11 }

tBgp4OTWithdrawnRouteLength      OBJECT-TYPE
    SYNTAX      Unsigned32
    MAX-ACCESS  accessible-for-notify
    STATUS      obsolete
    DESCRIPTION
        "The value of tBgp4OTWithdrawnRouteLength indicates the length of the
         route withdrawn as a result of optional-transitive path attribute
         error.

         This object was obsoleted in R11.0."
    ::= { tBgpNotificationObjs 12 }

tBgp4OTWithdrawnRoutePrefix      OBJECT-TYPE
    SYNTAX      OCTET STRING (SIZE (0..255))
    MAX-ACCESS  accessible-for-notify
    STATUS      obsolete
    DESCRIPTION
        "The value of tBgp4OTWithdrawnRoutePrefix indicates the prefix of the
         route withdrawn as a result of optional-transitive path attribute
         error.

         This object was obsoleted in R11.0 and replaced with
         tBgp4WithdrawnRoutePrefix."
    ::= { tBgpNotificationObjs 13 }

tBgpRouteInvalidReason           OBJECT-TYPE
    SYNTAX      DisplayString
    MAX-ACCESS  accessible-for-notify
    STATUS      current
    DESCRIPTION
        "The value of tBgpRouteInvalidReason indicates the reason why the
         received route is invalid."
    DEFVAL      { ''H }
    ::= { tBgpNotificationObjs 14 }

tBgpRouteNLRI                    OBJECT-TYPE
    SYNTAX      OCTET STRING (SIZE (0..255))
    MAX-ACCESS  accessible-for-notify
    STATUS      current
    DESCRIPTION
        "The value of tBgpRouteNLRI contains at most the first 255 octets of
         the NLRI (Network Layer Reachability Information) received in a route."
    ::= { tBgpNotificationObjs 15 }

tBgp4PathAttrType                OBJECT-TYPE
    SYNTAX      Integer32
    MAX-ACCESS  accessible-for-notify
    STATUS      current
    DESCRIPTION
        "The value of tBgp4PathAttrType indicates the path attribute type
         received from a remote BGP peer."
    ::= { tBgpNotificationObjs 16 }

tBgp4PathAttrLength              OBJECT-TYPE
    SYNTAX      Unsigned32
    MAX-ACCESS  accessible-for-notify
    STATUS      current
    DESCRIPTION
        "The value of tBgp4PathAttrLength indicates the length of path
         attribute received from a remote BGP peer."
    ::= { tBgpNotificationObjs 17 }

tBgp4PathAttribute               OBJECT-TYPE
    SYNTAX      OCTET STRING (SIZE (0..60))
    MAX-ACCESS  accessible-for-notify
    STATUS      current
    DESCRIPTION
        "The value of tBgp4PathAttribute indicates the path attribute value
         received from a remote BGP peer."
    ::= { tBgpNotificationObjs 18 }

tBgp4WithdrawnRoutePrefix        OBJECT-TYPE
    SYNTAX      OCTET STRING (SIZE (0..255))
    MAX-ACCESS  accessible-for-notify
    STATUS      current
    DESCRIPTION
        "The value of tBgp4WithdrawnRoutePrefix indicates the prefix of the
         route withdrawn as a result of path attribute error."
    ::= { tBgpNotificationObjs 19 }

tBgp4UpdateMessage               OBJECT-TYPE
    SYNTAX      OCTET STRING (SIZE (0..255))
    MAX-ACCESS  accessible-for-notify
    STATUS      current
    DESCRIPTION
        "The value of tBgp4UpdateMessage contains at most the first 255 octets
         of the UPDATE message received from a remote BGP peer."
    ::= { tBgpNotificationObjs 20 }

tBgp4BadErrorMessage             OBJECT-TYPE
    SYNTAX      OCTET STRING (SIZE (0..255))
    MAX-ACCESS  accessible-for-notify
    STATUS      current
    DESCRIPTION
        "The value of tBgp4BadErrorMessage contains at most the first 255
         octets of the Error part of the BGP packet."
    ::= { tBgpNotificationObjs 21 }

tBgp4BadErrorMessageType         OBJECT-TYPE
    SYNTAX      INTEGER {
        badNetworkError (1)
    }
    MAX-ACCESS  accessible-for-notify
    STATUS      current
    DESCRIPTION
        "The value of tBgp4BadErrorMessageType indicates the type of the error
         in the BGP packet."
    ::= { tBgpNotificationObjs 22 }

tBgpOldConvergenceState          OBJECT-TYPE
    SYNTAX      INTEGER {
        waiting   (1),
        started   (2),
        partial   (3),
        timeout   (4),
        converged (5)
    }
    MAX-ACCESS  accessible-for-notify
    STATUS      current
    DESCRIPTION
        "The value of tBgpOldConvergenceState indicates the convergence state
         of the address family."
    ::= { tBgpNotificationObjs 23 }

tBgpASN4Byte                     OBJECT-TYPE
    SYNTAX      Unsigned32
    MAX-ACCESS  accessible-for-notify
    STATUS      current
    DESCRIPTION
        "The value of tBgpASN4Byte indicates the autonomous system number for
         the dynamic neighbor."
    ::= { tBgpNotificationObjs 24 }

tmnxBgpConformance               OBJECT IDENTIFIER ::= { tmnxSRConfs 14 }

tmnxBgpCompliances               OBJECT IDENTIFIER ::= { tmnxBgpConformance 1 }

tmnxBgpV4v0Compliance            MODULE-COMPLIANCE
    STATUS      obsolete
    DESCRIPTION
        "The compliance statement for revision 4.0 of TIMETRA-BGP-MIB for
         management of extended BGP features on Nokia SROS series systems."
    MODULE
        MANDATORY-GROUPS {
            tmnxBgpInstanceV4v0Group,
            tmnxBgpInstanceParamsV4v0Group,
            tmnxBgpPeerGroupV4v0Group,
            tmnxBgpPeerGroupParamsV4v0Group,
            tmnxBgpPeerV4v0Group,
            tmnxBgpPeerParamsV4v0Group,
            tmnxBgpConfederationGroup,
            tmnxBgp4PathAttrGroup,
            tmnxBgpNotificationV4v0Group,
            tmnxBgpObsoleteV4v0Group,
            tmnxBgpObsoleteNotificationV4v0Group
        }
    ::= { tmnxBgpCompliances 4 }

tmnxBgpV5v0Compliance            MODULE-COMPLIANCE
    STATUS      obsolete
    DESCRIPTION
        "The compliance statement for revision 5.0 of TIMETRA-BGP-MIB for
         management of extended BGP features on Nokia SROS series systems."
    MODULE
        MANDATORY-GROUPS {
            tmnxBgpInstanceV4v0Group,
            tmnxBgpInstanceParamsV5v0Group,
            tmnxBgpPeerGroupV4v0Group,
            tmnxBgpPeerGroupParamsV5v0Group,
            tmnxBgpPeerV5v0Group,
            tmnxBgpPeerParamsV5v0Group,
            tmnxBgpConfederationGroup,
            tmnxBgp4PathAttrGroup,
            tmnxBgpNotificationV5v0Group,
            tmnxBgpObsoleteV5v0Group,
            tmnxBgpObsoleteNotificationV4v0Group
        }
    ::= { tmnxBgpCompliances 5 }

tmnxBgpV6v0Compliance            MODULE-COMPLIANCE
    STATUS      obsolete
    DESCRIPTION
        "The compliance statement for revision 6.0 of TIMETRA-BGP-MIB for
         management of extended BGP features on Nokia SROS series systems."
    MODULE
        MANDATORY-GROUPS {
            tmnxBgpInstanceV4v0Group,
            tmnxBgpInstanceParamsV5v0Group,
            tmnxBgpPeerGroupV4v0Group,
            tmnxBgpPeerGroupParamsV5v0Group,
            tmnxBgpPeerV6v0Group,
            tmnxBgpPeerParamsV5v0Group,
            tmnxBgpConfederationGroup,
            tmnxBgp4PathAttrGroup,
            tmnxBgpNotificationV5v0Group,
            tmnxBgpInstanceParamsV6v0Group,
            tmnxBgpPeerGroupParamsV6v0Group,
            tmnxBgpPeerParamsV6v0Group
        }
    ::= { tmnxBgpCompliances 6 }

tmnxBgpV7v0Compliance            MODULE-COMPLIANCE
    STATUS      obsolete
    DESCRIPTION
        "The compliance statement for revision 7.0 of TIMETRA-BGP-MIB for
         management of extended BGP features on Nokia SROS series systems."
    MODULE
        MANDATORY-GROUPS {
            tmnxBgpInstanceParamsV5v0Group,
            tmnxBgpPeerGroupParamsV5v0Group,
            tmnxBgpPeerParamsV5v0Group,
            tmnxBgp4PathAttrGroup,
            tmnxBgpNotificationV5v0Group,
            tmnxBgpInstanceParamsV6v0Group,
            tmnxBgpPeerGroupParamsV6v0Group,
            tmnxBgpPeerParamsV6v0Group,
            tmnxBgpPeeringPolicyV7v0Group,
            tmnxBgp4ByteASNV7v0Group,
            tmnxBgpInstanceV7v0Group,
            tmnxBgpPeerGroupV7v0Group,
            tmnxBgpPeerV7v0Group,
            tmnxBgpNotifyObjsV7v0Group,
            tmnxBgpNotificationV7v0Group
        }
    ::= { tmnxBgpCompliances 7 }

tmnxBgpV8v0Compliance            MODULE-COMPLIANCE
    STATUS      obsolete
    DESCRIPTION
        "The compliance statement for revision 8.0 of TIMETRA-BGP-MIB for
         management of extended BGP features on Nokia SROS series systems."
    MODULE
        MANDATORY-GROUPS {
            tmnxBgpInstanceParamsV5v0Group,
            tmnxBgpPeerGroupParamsV5v0Group,
            tmnxBgpPeerParamsV5v0Group,
            tmnxBgp4PathAttrGroup,
            tmnxBgpNotificationV5v0Group,
            tmnxBgpInstanceParamsV6v0Group,
            tmnxBgpPeerGroupParamsV6v0Group,
            tmnxBgpPeerParamsV6v0Group,
            tmnxBgpPeeringPolicyV7v0Group,
            tmnxBgp4ByteASNV7v0Group,
            tmnxBgpInstanceV7v0Group,
            tmnxBgpPeerGroupV7v0Group,
            tmnxBgpPeerV7v0Group,
            tmnxBgpNotifyObjsV7v0Group,
            tmnxBgpNotificationV7v0Group,
            tmnxBgpInstanceV8v0Group,
            tmnxBgpPeerV8v0Group,
            tmnxBgpGlobalV8v0Group
        }
    ::= { tmnxBgpCompliances 8 }

tmnxBgpV9v0Compliance            MODULE-COMPLIANCE
    STATUS      obsolete
    DESCRIPTION
        "The compliance statement for revision 9.0 of TIMETRA-BGP-MIB for
         management of extended BGP features on Nokia SROS series systems."
    MODULE
        MANDATORY-GROUPS {
            tmnxBgpInstanceParamsV5v0Group,
            tmnxBgpPeerGroupParamsV5v0Group,
            tmnxBgpPeerParamsV5v0Group,
            tmnxBgp4PathAttrGroup,
            tmnxBgpInstanceParamsV6v0Group,
            tmnxBgpPeerGroupParamsV6v0Group,
            tmnxBgpPeerParamsV6v0Group,
            tmnxBgpPeeringPolicyV7v0Group,
            tmnxBgp4ByteASNV7v0Group,
            tmnxBgpInstanceV7v0Group,
            tmnxBgpPeerGroupV7v0Group,
            tmnxBgpPeerV7v0Group,
            tmnxBgpNotifyObjsV7v0Group,
            tmnxBgpNotificationV7v0Group,
            tmnxBgpInstanceV8v0Group,
            tmnxBgpPeerV8v0Group,
            tmnxBgpGlobalV8v0Group,
            tmnxBgpPeerV9v0Group,
            tmnxBgpAddPathV9v0R4Group,
            tmnxBgpGlobalV9v0Group,
            tmnxBgpFlowSpecV9v0Group,
            tmnxBgpDisableCapNegoV9v0Group,
            tmnxBgpNotifyObjsV9v0Group,
            tmnxBgpNotificationV9v0Group
        }
    ::= { tmnxBgpCompliances 9 }

tmnxBgpV10v0Compliance           MODULE-COMPLIANCE
    STATUS      obsolete
    DESCRIPTION
        "The compliance statement for revision 10.0 of TIMETRA-BGP-MIB for
         management of extended BGP features on Nokia SROS series systems."
    MODULE
        MANDATORY-GROUPS {
            tmnxBgpInstanceParamsV5v0Group,
            tmnxBgpPeerGroupParamsV5v0Group,
            tmnxBgpPeerParamsV5v0Group,
            tmnxBgp4PathAttrGroup,
            tmnxBgpInstanceParamsV6v0Group,
            tmnxBgpPeerGroupParamsV6v0Group,
            tmnxBgpPeerParamsV6v0Group,
            tmnxBgpPeeringPolicyV10v0Group,
            tmnxBgp4ByteASNV7v0Group,
            tmnxBgpPeerGroupV10v0Group,
            tmnxBgpPeerV10v0Group,
            tmnxBgpNotifyObjsV7v0Group,
            tmnxBgpNotificationV7v0Group,
            tmnxBgpInstanceV8v0Group,
            tmnxBgpInstanceV10v0Group,
            tmnxBgpPeerV8v0Group,
            tmnxBgpGlobalV8v0Group,
            tmnxBgpPeerV9v0Group,
            tmnxBgpAddPathV9v0R4Group,
            tmnxBgpGlobalV9v0Group,
            tmnxBgpFlowSpecV9v0Group,
            tmnxBgpDisableCapNegoV9v0Group,
            tmnxBgpNotifyObjsV9v0Group,
            tmnxBgpNotificationV9v0Group,
            tmnxBgpGlobalV10v0Group,
            tmnxBgpPeeringPlcyV10v0Group,
            tmnxBgpRTConstraintV10v0Group
        }
    ::= { tmnxBgpCompliances 10 }

tmnxBgpV11v0Compliance           MODULE-COMPLIANCE
    STATUS      obsolete
    DESCRIPTION
        "The compliance statement for revision 11.0 of TIMETRA-BGP-MIB for
         management of extended BGP features on Nokia SROS series systems."
    MODULE
        MANDATORY-GROUPS {
            tmnxBgpInstanceParamsV5v0Group,
            tmnxBgpPeerGroupParamsV5v0Group,
            tmnxBgpPeerParamsV5v0Group,
            tmnxBgp4PathAttrGroup,
            tmnxBgpInstanceParamsV6v0Group,
            tmnxBgpPeerGroupParamsV6v0Group,
            tmnxBgpPeerParamsV6v0Group,
            tmnxBgpPeeringPolicyV10v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpGlobalV8v0Group,
            tmnxBgpPeerV9v0Group,
            tmnxBgpAddPathV9v0R4Group,
            tmnxBgpFlowSpecV9v0Group,
            tmnxBgpDisableCapNegoV9v0Group,
            tmnxBgpGlobalV10v0Group,
            tmnxBgpPeeringPlcyV10v0Group,
            tmnxBgpRTConstraintV10v0Group,
            tmnxBgpGlobalV11v0Group,
            tmnxBgpGlobalDCGroup,
            tmnxBgpDPOscilationV11v0Group,
            tmnxBgpNotifyObjsV11v0Group,
            tmnxBgpNotificationV11v0Group,
            tmnxBgpMvpnVrfImportGroup,
            tmnxBgpNHUnchangedGroup,
            tmnxBgpMcastIpv6Group,
            tmnxBgpPrefixOriginValidGroup
        }
    ::= { tmnxBgpCompliances 11 }

tmnxBgpV12v0Compliance           MODULE-COMPLIANCE
    STATUS      obsolete
    DESCRIPTION
        "The compliance statement for revision 12.0 of TIMETRA-BGP-MIB for
         management of extended BGP features on Nokia SROS series systems."
    MODULE
        MANDATORY-GROUPS {
            tmnxBgpResolveLabelRoutesGroup,
            tmnxBgpThirdPartyNHGroup,
            tmnxBgpInstanceV12v0Group,
            tmnxBgpPeerGroupV12v0Group,
            tmnxBgpPeerV12v0Group,
            tmnxBgpObsoleteV12v0Group,
            tmnxBgpNotificationV12v0Group,
            tmnxBgpNotifyObjsV12v0Group
        }
    ::= { tmnxBgpCompliances 12 }

tmnxBgpV13v0Compliance           MODULE-COMPLIANCE
    STATUS      obsolete
    DESCRIPTION
        "The compliance statement for revision 13.0 of TIMETRA-BGP-MIB for
         management of extended BGP features on Nokia SROS series systems."
    MODULE
        MANDATORY-GROUPS {
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpInstanceV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgpPeerParamsV5v0Group,
            tmnxBgp4PathAttrGroup,
            tmnxBgpInstanceParamsV6v0Group,
            tmnxBgpPeerGroupParamsV6v0Group,
            tmnxBgpPeerParamsV6v0Group,
            tmnxBgpPeeringPolicyV10v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpAddPathV9v0R4Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpNotifyObjsV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group
        }
    ::= { tmnxBgpCompliances 13 }

tmnxBgpV14v0Compliance           MODULE-COMPLIANCE
    STATUS      obsolete
    DESCRIPTION
        "The compliance statement for revision 14.0 of TIMETRA-BGP-MIB for
         management of extended BGP features on Nokia SROS series systems."
    MODULE
        MANDATORY-GROUPS {
            tmnxBgpMultiPathV14v0Group,
            tmnxBgpPeerNgV14v0Group,
            tmnxBgpLabelRtTunnelV14v0Group,
            tmnxBgpShortcutTunnelV14v0Group,
            tmnxBgpEntropyLabelV14v0Group,
            tmnxBgpRibRouteImportV14v0Group,
            tmnxBgpLblRibSeparateV14v0Group,
            tmnxPeerNgV14v1Group,
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgpPeerParamsV5v0Group,
            tmnxBgp4PathAttrGroup,
            tmnxBgpInstanceParamsV6v0Group,
            tmnxBgpPeerGroupParamsV6v0Group,
            tmnxBgpPeerParamsV6v0Group,
            tmnxBgpPeeringPolicyV10v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpAddPathV9v0R4Group,
            tmnxBgpFlowSpecV9v0Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpNotifyObjsV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group,
            tmnxBgpInstanceV14v0Group,
            tmnxBgpInstanceParamsV14v0Group,
            tmnxBgpInstanceParamsV14v4Group,
            tmnxBgpPeerGroupParamsV14v4Group
        }
    ::= { tmnxBgpCompliances 14 }

tmnxBgpV15v0Compliance           MODULE-COMPLIANCE
    STATUS      obsolete
    DESCRIPTION
        "The compliance statement for revision 15.0 of TIMETRA-BGP-MIB for
         management of extended BGP features on Nokia SROS series systems."
    MODULE
        MANDATORY-GROUPS {
            tmnxBgpMultiPathV14v0Group,
            tmnxBgpLabelRtTunnelV14v0Group,
            tmnxBgpShortcutTunnelV14v0Group,
            tmnxBgpEntropyLabelV14v0Group,
            tmnxBgpRibRouteImportV14v0Group,
            tmnxPeerNgV14v1Group,
            tmnxPeerNgV15v0Group,
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgp4PathAttrGroup,
            tmnxBgpInstanceParamsV6v0Group,
            tmnxBgpPeerGroupParamsV6v0Group,
            tmnxBgpPeerParamsV6v0Group,
            tmnxBgpPeeringPolicyV10v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group,
            tmnxBgpInstanceV14v0Group,
            tmnxBgpInstanceParamsV14v0Group,
            tmnxBgpInstanceParamsV14v4Group,
            tmnxBgpPeerGroupParamsV14v4Group,
            tmnxBgpPeerParamsGroup,
            tmnxBgpInstanceParamsV15v0Group,
            tmnxBgpLabelRtTunnelV15v0Group,
            tmnxBgpORRV15v0Group,
            tmnxBgpWeightedEcmpGroup,
            tmnxBgpObjectsV15v0ObsoleteGroup,
            tmnxBgpObsoleteNotifyV15v0Group,
            tmnxBgpNotifyObjsV15v0Group,
            tmnxBgpObsoleteNfyObjsV15v0Group,
            tmnxBgpAddPathV15v0Group,
            tmnxBgpLblRibSeparateV15v0Group,
            tmnxBgpEnforceFirstASGroup,
            tmnxBgpInstanceParamsExtGroup,
            tmnxBgpLLGRV15v0Group,
            tmnxBgpNotificationV15v0Group,
            tmnxBgpLocalAddressV15v4Group
        }
    ::= { tmnxBgpCompliances 15 }

tmnxBgpV16v0Compliance           MODULE-COMPLIANCE
    STATUS      obsolete
    DESCRIPTION
        "The compliance statement for revision 16.0 of TIMETRA-BGP-MIB for
         management of extended BGP features on Nokia SROS series systems."
    MODULE
        MANDATORY-GROUPS {
            tmnxBgpMultiPathV14v0Group,
            tmnxBgpLabelRtTunnelV14v0Group,
            tmnxBgpShortcutTunnelV14v0Group,
            tmnxBgpEntropyLabelV14v0Group,
            tmnxBgpRibRouteImportV14v0Group,
            tmnxPeerNgV14v1Group,
            tmnxPeerNgV15v0Group,
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgp4PathAttrGroup,
            tmnxBgpInstanceParamsV6v0Group,
            tmnxBgpPeerGroupParamsV6v0Group,
            tmnxBgpPeerParamsV6v0Group,
            tmnxBgpPeeringPolicyV16v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group,
            tmnxBgpInstanceV14v0Group,
            tmnxBgpInstanceParamsV14v0Group,
            tmnxBgpInstanceParamsV14v4Group,
            tmnxBgpPeerGroupParamsV14v4Group,
            tmnxBgpPeerParamsGroup,
            tmnxBgpInstanceParamsV15v0Group,
            tmnxBgpLabelRtTunnelV15v0Group,
            tmnxBgpORRV15v0Group,
            tmnxBgpWeightedEcmpGroup,
            tmnxBgpObjectsV15v0ObsoleteGroup,
            tmnxBgpObsoleteNotifyV15v0Group,
            tmnxBgpNotifyObjsV15v0Group,
            tmnxBgpObsoleteNfyObjsV15v0Group,
            tmnxBgpAddPathV15v0Group,
            tmnxBgpLblRibSeparateV15v0Group,
            tmnxBgpEnforceFirstASGroup,
            tmnxBgpInstanceParamsExtGroup,
            tmnxBgpLLGRV15v0Group,
            tmnxBgpNotificationV15v0Group,
            tmnxBgpLocalAddressV15v4Group,
            tmnxBgpIpv6NhAdvAndResV16v0Group,
            tmnxBgpBypassMRAITimerV16v0Group,
            tmnxBgpAdminTagsV16v0Group,
            tmnxPeerNgV16v0Group,
            tmnxBgpLargeCommsV16v0Group,
            tmnxBgpNHResFilterV16v0Group,
            tmnxBgpLabelSecurityGroup,
            tmnxBgpRibApiGroup,
            tmnxBgpTunnelMplsFwdPlcyGroup,
            tmnxBgpLinkBandwidthGroup,
            tmnxBgpORRV16v0Group,
            tmnxBgpTunnelSrOspf3,
            tmnxBgpLoopDetectThreshold,
            tmnxBgpSrTePolicyIpv6Group
        }
    ::= { tmnxBgpCompliances 16 }

tmnxBgpV19v0Compliance           MODULE-COMPLIANCE
    STATUS      obsolete
    DESCRIPTION
        "The compliance statement for revision 19.0 of TIMETRA-BGP-MIB for
         management of extended BGP features on Nokia SROS series systems."
    MODULE
        MANDATORY-GROUPS {
            tmnxBgpNHResGroup,
            tmnxBgpConvergenceGroup,
            tmnxBgpNotificationV19v0Group,
            tmnxBgpInstanceV19v0Group,
            tmnxBgpDefaultOriginate,
            tBgpPeerGrpDynNbrAsGroup,
            tmnxBgpPreferenceGroup,
            tmnxBgpEBGPRejectWithoutPolicy,
            tmnxBgpRemovePrivateReplace,
            tmnxBgpBlockPrefixSIDGroup,
            tmnxPeerNgV19v5Group,
            tmnxBgpNotifyObjsV19v0Group,
            tmnxBgpTcpMss
        }
    ::= { tmnxBgpCompliances 17 }

tmnxBgpSegRoutingV19Compliance   MODULE-COMPLIANCE
    STATUS      obsolete
    DESCRIPTION
        "The compliance statement for revision 19.10 of TIMETRA-BGP-MIB for
         management of extended BGP features of Nokia SROS series systems."
    MODULE
        MANDATORY-GROUPS {
            tmnxBgpSegRoutingV19Group
        }
    ::= { tmnxBgpCompliances 18 }

tmnxBgpV20v0Compliance           MODULE-COMPLIANCE
    STATUS      obsolete
    DESCRIPTION
        "The compliance statement for revision 20 of TIMETRA-BGP-MIB for
         management of extended BGP features of Nokia SROS series systems."
    MODULE
        MANDATORY-GROUPS {
            tmnxBgpLabelIpv6V20Group,
            tmnxBgpTunnelMetric,
            tmnxBgpEngressEng,
            tmnxBgpNHV20v0Group,
            tmnxBgpLRV20v0Group,
            tmnxBgpTunnelFlexAlgoFb,
            tmnxBgpLUStats
        }
    ::= { tmnxBgpCompliances 19 }

tmnxBgpV21v0Compliance           MODULE-COMPLIANCE
    STATUS      obsolete
    DESCRIPTION
        "The compliance statement for revision 21 of TIMETRA-BGP-MIB for
         management of extended BGP features of Nokia SROS series systems."
    MODULE
        MANDATORY-GROUPS {
            tmnxBgpTunnelPreference,
            tmnxBgpLabelRoutesUseBgpRoutes,
            tmnxBgpSrv6,
            tmnxBgpGlobalV21v0Group,
            tmnxBgpSubconfVpnFwding,
            tmnxBgpSelLblIpPri,
            tmnxBgpEvpnAddPaths,
            tmnxBgpSrv6Tlv,
            tmnxBgpDpath,
            tmnxBgpNHPreferTransportFRR,
            tmnxBgpFlowSpecVpn
        }
    ::= { tmnxBgpCompliances 20 }

tmnxBgpV22v0Compliance           MODULE-COMPLIANCE
    STATUS      obsolete
    DESCRIPTION
        "The compliance statement for revision 22 of TIMETRA-BGP-MIB for
         management of extended BGP features of Nokia SROS  series systems."
    MODULE
        MANDATORY-GROUPS {
            tmnxBgpAddPathV22v2Group,
            tmnxBgpEPEBgpLUV22v0Group,
            tmnxBgpObjectsV22v2ObsoleteGroup,
            tmnxBgpTunnelMetricPrefMed,
            tmnxBgpPGDynNbrIfGroup,
            tmnxBgpSrv6PolicyGroup,
            tmnxBgpPGDynNbrIfMaxSessNtfnGrp,
            tmnxBgpEvpnLinkBWGroup,
            tmnxBgpPeerFsmTimeGroup,
            tmnxBgpSrv6MicroSegmentGroup,
            tmnxBgpSelLabelIpInstallGroup
        }
    ::= { tmnxBgpCompliances 21 }

tmnxBgpV23v0Compliance           MODULE-COMPLIANCE
    STATUS      obsolete
    DESCRIPTION
        "The compliance statement for revision 23 of TIMETRA-BGP-MIB for
         management of extended BGP features of Nokia SROS  series systems."
    MODULE
        MANDATORY-GROUPS {
            tmnxBgpMultiPathV14v0Group,
            tmnxBgpLabelRtTunnelV14v0Group,
            tmnxBgpShortcutTunnelV14v0Group,
            tmnxBgpEntropyLabelV14v0Group,
            tmnxBgpRibRouteImportV14v0Group,
            tmnxPeerNgV14v1Group,
            tmnxPeerNgV15v0Group,
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgp4PathAttrGroup,
            tmnxBgpInstanceParamsV6v0Group,
            tmnxBgpPeerGroupParamsV6v0Group,
            tmnxBgpPeerParamsV6v0Group,
            tmnxBgpPeeringPolicyV16v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group,
            tmnxBgpInstanceV14v0Group,
            tmnxBgpInstanceParamsV14v0Group,
            tmnxBgpInstanceParamsV14v4Group,
            tmnxBgpPeerGroupParamsV14v4Group,
            tmnxBgpPeerParamsGroup,
            tmnxBgpInstanceParamsV15v0Group,
            tmnxBgpLabelRtTunnelV15v0Group,
            tmnxBgpORRV15v0Group,
            tmnxBgpWeightedEcmpGroup,
            tmnxBgpObjectsV15v0ObsoleteGroup,
            tmnxBgpObsoleteNotifyV15v0Group,
            tmnxBgpNotifyObjsV15v0Group,
            tmnxBgpObsoleteNfyObjsV15v0Group,
            tmnxBgpAddPathV15v0Group,
            tmnxBgpLblRibSeparateV15v0Group,
            tmnxBgpEnforceFirstASGroup,
            tmnxBgpInstanceParamsExtGroup,
            tmnxBgpLLGRV15v0Group,
            tmnxBgpNotificationV15v0Group,
            tmnxBgpLocalAddressV15v4Group,
            tmnxBgpIpv6NhAdvAndResV16v0Group,
            tmnxBgpBypassMRAITimerV16v0Group,
            tmnxBgpAdminTagsV16v0Group,
            tmnxPeerNgV16v0Group,
            tmnxBgpLargeCommsV16v0Group,
            tmnxBgpNHResFilterV16v0Group,
            tmnxBgpLabelSecurityGroup,
            tmnxBgpRibApiGroup,
            tmnxBgpTunnelMplsFwdPlcyGroup,
            tmnxBgpLinkBandwidthGroup,
            tmnxBgpORRV16v0Group,
            tmnxBgpTunnelSrOspf3,
            tmnxBgpLoopDetectThreshold,
            tmnxBgpSrTePolicyIpv6Group,
            tmnxBgpNHResGroup,
            tmnxBgpConvergenceGroup,
            tmnxBgpNotificationV19v0Group,
            tmnxBgpInstanceV19v0Group,
            tmnxBgpDefaultOriginate,
            tBgpPeerGrpDynNbrAsGroup,
            tmnxBgpPreferenceGroup,
            tmnxBgpEBGPRejectWithoutPolicy,
            tmnxBgpRemovePrivateReplace,
            tmnxBgpBlockPrefixSIDGroup,
            tmnxPeerNgV19v5Group,
            tmnxBgpNotifyObjsV19v0Group,
            tmnxBgpTcpMss,
            tmnxBgpSegRoutingV19Group,
            tmnxBgpLabelIpv6V20Group,
            tmnxBgpTunnelMetric,
            tmnxBgpEngressEng,
            tmnxBgpNHV20v0Group,
            tmnxBgpLRV20v0Group,
            tmnxBgpTunnelFlexAlgoFb,
            tmnxBgpLUStats,
            tmnxBgpTunnelPreference,
            tmnxBgpLabelRoutesUseBgpRoutes,
            tmnxBgpSrv6,
            tmnxBgpGlobalV21v0Group,
            tmnxBgpSubconfVpnFwding,
            tmnxBgpSelLblIpPri,
            tmnxBgpEvpnAddPaths,
            tmnxBgpSrv6Tlv,
            tmnxBgpDpath,
            tmnxBgpNHPreferTransportFRR,
            tmnxBgpFlowSpecVpn,
            tmnxBgpAddPathV22v2Group,
            tmnxBgpEPEBgpLUV22v0Group,
            tmnxBgpObjectsV22v2ObsoleteGroup,
            tmnxBgpTunnelMetricPrefMed,
            tmnxBgpPGDynNbrIfGroup,
            tmnxBgpSrv6PolicyGroup,
            tmnxBgpPGDynNbrIfMaxSessNtfnGrp,
            tmnxBgpEvpnLinkBWGroup,
            tmnxBgpPeerFsmTimeGroup,
            tmnxBgpSrv6MicroSegmentGroup,
            tmnxBgpSelLabelIpInstallGroup,
            tmnxBgpBfdStrictMode,
            tmnxBgpGlobalV23v0Group,
            tmnxBgpLeakedRoutesStaticGroup,
            tmnxBgpPfxLmtHoldExcessGroup,
            tmnxBgpAttrSetGroup,
            tmnxBgpEnforceUntagRtGroup
        }
    ::= { tmnxBgpCompliances 22 }

tmnxBgpV24v0Compliance           MODULE-COMPLIANCE
    STATUS      current
    DESCRIPTION
        "The compliance statement for revision 24 of TIMETRA-BGP-MIB for
         management of extended BGP features of Nokia SROS  series systems."
    MODULE
        MANDATORY-GROUPS {
            tBgpSrv6UpaTriggerNextHopGroup,
            tmnxBgpLegacyFaultToleranceGroup,
            tmnxBgpLUEcmpGroup
        }
    ::= { tmnxBgpCompliances 23 }

tmnxBgpSRLV24v0Compliance        MODULE-COMPLIANCE
    STATUS      current
    DESCRIPTION
        "The compliance statement for revision 24 of TIMETRA-BGP-MIB for
         management of extended BGP features of Nokia SRLINUX series systems."
    MODULE
        MANDATORY-GROUPS {
            tmnxBgpPeerNgOperSRLGroup
        }
    ::= { tmnxBgpCompliances 24 }

tmnxBgpV25v0Compliance           MODULE-COMPLIANCE
    STATUS      current
    DESCRIPTION
        "The compliance statement for revision 25 of TIMETRA-BGP-MIB for
         management of extended BGP features of Nokia SROS  series systems."
    MODULE
        MANDATORY-GROUPS {
            tmnxBgpMultiPathV14v0Group,
            tmnxBgpLabelRtTunnelV14v0Group,
            tmnxBgpShortcutTunnelV14v0Group,
            tmnxBgpEntropyLabelV14v0Group,
            tmnxBgpRibRouteImportV14v0Group,
            tmnxPeerNgV14v1Group,
            tmnxPeerNgV15v0Group,
            tmnxBgpPeerGroupV13v0Group,
            tmnxBgpNotificationV13v0Group,
            tmnxBgpLinkBandwidthExtCommGroup,
            tmnxBgpRibLeakImportV13v0Group,
            tmnxBgpShortcutTunnelV13v0Group,
            tmnxBgpLabelRtTunnelV13v0Group,
            tmnxBgpDynamicPeerLmtV13v0Group,
            tmnxBgpPeerGroupV13v1Group,
            tmnxBgpGlobalV13v0Group,
            tmnxBgpGlobalV13v1Group,
            tmnxBgpPeerV13v0Group,
            tmnxBgpObsoleteV13v0Group,
            tmnxBgpNotificationV13v1Group,
            tmnxBgpObsoletedNtfnV13v0Group,
            tmnxBgpInstanceParamsV5v0Group,
            tmnxBgpPeerGroupParamsV5v0Group,
            tmnxBgp4PathAttrGroup,
            tmnxBgpInstanceParamsV6v0Group,
            tmnxBgpPeerGroupParamsV6v0Group,
            tmnxBgpPeerParamsV6v0Group,
            tmnxBgpPeeringPolicyV16v0Group,
            tmnxBgp4ByteASNV7v0Group,
            tmnxBgpPeerGroupV11v0Group,
            tmnxBgpNotifyObjsV7v0Group,
            tmnxBgpNotificationV7v0Group,
            tmnxBgpInstanceV8v0Group,
            tmnxBgpPeerV8v0Group,
            tmnxBgpPeerV9v0Group,
            tmnxBgpDisableCapNegoV9v0Group,
            tmnxBgpGlobalV10v0Group,
            tmnxBgpPeeringPlcyV10v0Group,
            tmnxBgpRTConstraintV10v0Group,
            tmnxBgpGlobalDCGroup,
            tmnxBgpDPOscilationV11v0Group,
            tmnxBgpMvpnVrfImportGroup,
            tmnxBgpNHUnchangedGroup,
            tmnxBgpMcastIpv6Group,
            tmnxBgpPrefixOriginValidGroup,
            tmnxBgpResolveLabelRoutesGroup,
            tmnxBgpThirdPartyNHGroup,
            tmnxBgpObsoleteV12v0Group,
            tmnxBgpNotificationV12v0Group,
            tmnxBgpNotifyObjsV12v0Group,
            tmnxBgpPeerNgV13v0Group,
            tmnxBgpPeerNgDynamicV13v0Group,
            tmnxBgpPeerNgEvpnMplsV13v0Group,
            tmnxBgpDynPeerLmtNtfnV13v0Group,
            tmnxBgpInstanceV14v0Group,
            tmnxBgpInstanceParamsV14v0Group,
            tmnxBgpInstanceParamsV14v4Group,
            tmnxBgpPeerGroupParamsV14v4Group,
            tmnxBgpPeerParamsGroup,
            tmnxBgpInstanceParamsV15v0Group,
            tmnxBgpLabelRtTunnelV15v0Group,
            tmnxBgpORRV15v0Group,
            tmnxBgpWeightedEcmpGroup,
            tmnxBgpObjectsV15v0ObsoleteGroup,
            tmnxBgpObsoleteNotifyV15v0Group,
            tmnxBgpNotifyObjsV15v0Group,
            tmnxBgpObsoleteNfyObjsV15v0Group,
            tmnxBgpAddPathV15v0Group,
            tmnxBgpLblRibSeparateV15v0Group,
            tmnxBgpEnforceFirstASGroup,
            tmnxBgpInstanceParamsExtGroup,
            tmnxBgpLLGRV15v0Group,
            tmnxBgpNotificationV15v0Group,
            tmnxBgpLocalAddressV15v4Group,
            tmnxBgpIpv6NhAdvAndResV16v0Group,
            tmnxBgpBypassMRAITimerV16v0Group,
            tmnxBgpAdminTagsV16v0Group,
            tmnxPeerNgV16v0Group,
            tmnxBgpLargeCommsV16v0Group,
            tmnxBgpNHResFilterV16v0Group,
            tmnxBgpLabelSecurityGroup,
            tmnxBgpRibApiGroup,
            tmnxBgpTunnelMplsFwdPlcyGroup,
            tmnxBgpLinkBandwidthGroup,
            tmnxBgpORRV16v0Group,
            tmnxBgpTunnelSrOspf3,
            tmnxBgpLoopDetectThreshold,
            tmnxBgpSrTePolicyIpv6Group,
            tmnxBgpNHResGroup,
            tmnxBgpConvergenceGroup,
            tmnxBgpNotificationV19v0Group,
            tmnxBgpInstanceV19v0Group,
            tmnxBgpDefaultOriginate,
            tBgpPeerGrpDynNbrAsGroup,
            tmnxBgpPreferenceGroup,
            tmnxBgpEBGPRejectWithoutPolicy,
            tmnxBgpRemovePrivateReplace,
            tmnxBgpBlockPrefixSIDGroup,
            tmnxPeerNgV19v5Group,
            tmnxBgpNotifyObjsV19v0Group,
            tmnxBgpTcpMss,
            tmnxBgpSegRoutingV19Group,
            tmnxBgpLabelIpv6V20Group,
            tmnxBgpTunnelMetric,
            tmnxBgpEngressEng,
            tmnxBgpNHV20v0Group,
            tmnxBgpLRV20v0Group,
            tmnxBgpTunnelFlexAlgoFb,
            tmnxBgpLUStats,
            tmnxBgpTunnelPreference,
            tmnxBgpLabelRoutesUseBgpRoutes,
            tmnxBgpSrv6,
            tmnxBgpGlobalV21v0Group,
            tmnxBgpSubconfVpnFwding,
            tmnxBgpSelLblIpPri,
            tmnxBgpEvpnAddPaths,
            tmnxBgpSrv6Tlv,
            tmnxBgpNHPreferTransportFRR,
            tmnxBgpFlowSpecVpn,
            tmnxBgpAddPathV22v2Group,
            tmnxBgpEPEBgpLUV22v0Group,
            tmnxBgpObjectsV22v2ObsoleteGroup,
            tmnxBgpTunnelMetricPrefMed,
            tmnxBgpPGDynNbrIfGroup,
            tmnxBgpSrv6PolicyGroup,
            tmnxBgpPGDynNbrIfMaxSessNtfnGrp,
            tmnxBgpEvpnLinkBWGroup,
            tmnxBgpPeerFsmTimeGroup,
            tmnxBgpSrv6MicroSegmentGroup,
            tmnxBgpSelLabelIpInstallGroup,
            tmnxBgpBfdStrictMode,
            tmnxBgpGlobalV23v0Group,
            tmnxBgpLeakedRoutesStaticGroup,
            tmnxBgpPfxLmtHoldExcessGroup,
            tmnxBgpAttrSetGroup,
            tmnxBgpEnforceUntagRtGroup,
            tmnxBgpDpath25v0
        }
    ::= { tmnxBgpCompliances 25 }

tmnxBgpGroups                    OBJECT IDENTIFIER ::= { tmnxBgpConformance 2 }

tmnxBgpConfederationGroup        OBJECT-GROUP
    OBJECTS     {
        tBgpConfederationTableLastChanged,
        tBgpConfederationRowStatus
    }
    STATUS      obsolete
    DESCRIPTION
        "The group of objects supporting management of extended BGP
         confederations on Nokia SROS series systems."
    ::= { tmnxBgpGroups 5 }

tmnxBgp4PathAttrGroup            OBJECT-GROUP
    OBJECTS     {
        tBgp4PathAttrOriginID,
        tBgp4PathAttrClusterList,
        tBgp4PathAttrCommunity,
        tBgp4PathAttrExtCommunity
    }
    STATUS      current
    DESCRIPTION
        "The group of objects supporting management of extended BGP4 path
         attributes on Nokia SROS series systems."
    ::= { tmnxBgpGroups 6 }

tmnxBgpPeerV4v0Group             OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgMinASOrigination,
        tBgpPeerNgDampening,
        tBgpPeerNgLocalAddress,
        tBgpPeerNgLocalAddressType,
        tBgpPeerNgLocalAS,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerAS,
        tBgpPeerNgPeerType,
        tBgpPeerNgPreference,
        tBgpPeerNgRemovePrivateAS,
        tBgpPeerNgLastChanged,
        tBgpPeerNgInheritance,
        tBgpPeerNgImportPolicy1,
        tBgpPeerNgImportPolicy2,
        tBgpPeerNgImportPolicy3,
        tBgpPeerNgImportPolicy4,
        tBgpPeerNgImportPolicy5,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperPathsSupByDamping,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV6ReceivedPaths,
        tBgpPeerNgOperV6SuppPathsDamping,
        tBgpPeerNgOperVpnReceivedPaths
    }
    STATUS      obsolete
    DESCRIPTION
        "The group of objects supporting management of extended BGP peers on
         Nokia SROS series systems."
    ::= { tmnxBgpGroups 19 }

tmnxBgpInstanceV4v0Group         OBJECT-GROUP
    OBJECTS     {
        tBgpInstanceTableLastChanged,
        tBgpInstanceRowStatus,
        tBgpInstanceShutdown,
        tBgpInstanceDescription,
        tBgpInstanceAlwaysCompareMED,
        tBgpInstanceAsPathIgnore,
        tBgpInstanceBgpId,
        tBgpInstanceConnectRetry,
        tBgpInstanceHoldTime,
        tBgpInstanceKeepAlive,
        tBgpInstanceMinASOrigination,
        tBgpInstanceDampening,
        tBgpInstanceLocalAS,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceConfederationAS,
        tBgpInstanceImportPolicy1,
        tBgpInstanceImportPolicy2,
        tBgpInstanceImportPolicy3,
        tBgpInstanceImportPolicy4,
        tBgpInstanceImportPolicy5,
        tBgpInstanceExportPolicy1,
        tBgpInstanceExportPolicy2,
        tBgpInstanceExportPolicy3,
        tBgpInstanceExportPolicy4,
        tBgpInstanceExportPolicy5,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceIgpShortcut,
        tBgpInstanceDisallowIgp,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn
    }
    STATUS      obsolete
    DESCRIPTION
        "The group of objects supporting management of each extended BGP
         instance on Nokia SROS series systems."
    ::= { tmnxBgpGroups 20 }

tmnxBgpObsoleteV4v0Group         OBJECT-GROUP
    OBJECTS     {
        tBgpPeerPeerGroup,
        tBgpPeerRowStatus,
        tBgpPeerShutdown,
        tBgpPeerDescription,
        tBgpPeerConnectRetry,
        tBgpPeerHoldTime,
        tBgpPeerKeepAlive,
        tBgpPeerMinASOrigination,
        tBgpPeerDampening,
        tBgpPeerLocalAddress,
        tBgpPeerLocalAS,
        tBgpPeerLocalPreference,
        tBgpPeerLoopDetect,
        tBgpPeerMinRouteAdvertisement,
        tBgpPeerMaxPrefix,
        tBgpPeerMEDSource,
        tBgpPeerMEDValue,
        tBgpPeerMultihop,
        tBgpPeerNextHopSelf,
        tBgpPeerNoAggregatorID,
        tBgpPeerPassive,
        tBgpPeerPeerAS,
        tBgpPeerPeerType,
        tBgpPeerPreference,
        tBgpPeerRemovePrivateAS,
        tBgpPeerLastChanged,
        tBgpPeerInheritance,
        tBgpPeerImportPolicy1,
        tBgpPeerImportPolicy2,
        tBgpPeerImportPolicy3,
        tBgpPeerImportPolicy4,
        tBgpPeerImportPolicy5,
        tBgpPeerExportPolicy1,
        tBgpPeerExportPolicy2,
        tBgpPeerExportPolicy3,
        tBgpPeerExportPolicy4,
        tBgpPeerExportPolicy5,
        tBgpPeerOperStatus,
        tBgpPeerLocalASPrivate,
        tBgpPeerMd5Auth,
        tBgpPeerMd5AuthKey,
        tBgpPeerClusterId,
        tBgpPeerDisableClientReflect,
        tBgpPeerGracefulRestart,
        tBgpPeerGRRestartTime,
        tBgpPeerGRStaleRoute,
        tBgpPeerGRAdminState,
        tBgpPeerGROperState,
        tBgpPeerFamily,
        tBgpPeerVpnRemoteFamily,
        tBgpPeerVpnApplyImport,
        tBgpPeerVpnApplyExport,
        tBgpPeerVpnLocalCaps,
        tBgpPeerVpnRemoteCaps,
        tBgpPeerConnState,
        tBgpPeerASOverride,
        tBgpPeerOrf,
        tBgpPeerExtCommsOrf,
        tBgpPeerExtCommsSendOrf,
        tBgpPeerExtCommsRecvOrf,
        tBgpPeerOperMsgOctetsRcvd,
        tBgpPeerOperMsgOctetsSent,
        tBgpPeerOperInputQueueMessages,
        tBgpPeerOperOutputQueueMessages,
        tBgpPeerOperReceivedPrefixes,
        tBgpPeerOperSentPrefixes,
        tBgpPeerOperActivePrefixes,
        tBgpPeerOperReceivedPaths,
        tBgpPeerOperPathsSuppressedByDamping,
        tBgpPeerOperFlaps,
        tBgpPeerOperLastState,
        tBgpPeerOperLastEvent,
        tBgpPeerOperVpnReceivedPrefixes,
        tBgpPeerOperVpnSentPrefixes,
        tBgpPeerOperVpnActivePrefixes,
        tBgpPeerSendOrfRTRowStatus,
        tBgpPeerOperGRSupport,
        tBgpPeerOperGRFamilyRestart,
        tBgpPeerOperGRFamilyFwding,
        tBgpPeerOperGRFamilyNegotiated,
        tBgpPeerOperGRRecvEOR,
        tBgpPeerOperGRSendEOR,
        tBgpPeerOperGRStaleRoutesTime,
        tBgpPeerOperGRRequestRestartTime,
        tBgpPeerOperGRStatus,
        tBgpPeerOperNumRestarts,
        tBgpPeerOperLastRestartTime,
        tBgpPeerOperV6ReceivedPrefixes,
        tBgpPeerOperV6SentPrefixes,
        tBgpPeerOperV6ActivePrefixes,
        tBgpPeerOperV6ReceivedPaths,
        tBgpPeerOperV6SuppPathsDamping,
        tBgpPeerOperVpnReceivedPaths,
        tBgpPeerParamsInheritance,
        tBgpPeerDisableFEFailover,
        tBgpPeerDisableComms,
        tBgpPeerDisableExtComms,
        tBgpPeerDefaultOriginate,
        tBgpPeerAdvertiseInactiveRts,
        tBgpPeerMinTTLValue,
        tBgpPeerTTLLogId,
        tBgpPeerGroupLocalAddress
    }
    STATUS      obsolete
    DESCRIPTION
        "The group of objects supporting management of extended BGP peers on
         Nokia SROS series systems."
    ::= { tmnxBgpGroups 21 }

tmnxBgpPeerParamsV4v0Group       OBJECT-GROUP
    OBJECTS     {
        tBgpPeerNgParamsInheritance,
        tBgpPeerNgDisableFEFailover,
        tBgpPeerNgDisableComms,
        tBgpPeerNgDisableExtComms,
        tBgpPeerNgDefaultOriginate,
        tBgpPeerNgAdvertiseInactiveRts,
        tBgpPeerNgMinTTLValue,
        tBgpPeerNgTracking
    }
    STATUS      obsolete
    DESCRIPTION
        "The group of objects supporting management of extended BGP peer
         parameters on Nokia SROS series systems."
    ::= { tmnxBgpGroups 22 }

tmnxBgpPeerGroupParamsV4v0Group  OBJECT-GROUP
    OBJECTS     {
        tBgpPGParamsInheritance,
        tBgpPGDisableFEFailover,
        tBgpPGDisableComms,
        tBgpPGDisableExtComms,
        tBgpPGDefaultOriginate,
        tBgpPGAdvertiseInactiveRts,
        tBgpPGMinTTLValue,
        tBgpPGTTLLogId,
        tBgpPGLocalAddressType,
        tBgpPGLocalAddress,
        tBgpPGPeerTracking
    }
    STATUS      obsolete
    DESCRIPTION
        "The group of objects supporting management of extended BGP Peer Group
         parameters on Nokia SROS series systems."
    ::= { tmnxBgpGroups 23 }

tmnxBgpPeerGroupV4v0Group        OBJECT-GROUP
    OBJECTS     {
        tBgpPeerGroupTableLastChanged,
        tBgpPeerGroupTableSpinlock,
        tBgpPeerGroupName,
        tBgpPeerGroupRowStatus,
        tBgpPeerGroupShutdown,
        tBgpPeerGroupDescription,
        tBgpPeerGroupConnectRetry,
        tBgpPeerGroupHoldTime,
        tBgpPeerGroupKeepAlive,
        tBgpPeerGroupMinASOrigination,
        tBgpPeerGroupDampening,
        tBgpPeerGroupLocalAS,
        tBgpPeerGroupLocalPreference,
        tBgpPeerGroupLoopDetect,
        tBgpPeerGroupMinRouteAdvertisement,
        tBgpPeerGroupMaxPrefix,
        tBgpPeerGroupMEDSource,
        tBgpPeerGroupMEDValue,
        tBgpPeerGroupMultihop,
        tBgpPeerGroupNextHopSelf,
        tBgpPeerGroupNoAggregatorID,
        tBgpPeerGroupPassive,
        tBgpPeerGroupPeerAS,
        tBgpPeerGroupPeerType,
        tBgpPeerGroupPreference,
        tBgpPeerGroupRemovePrivateAS,
        tBgpPeerGroupLastChanged,
        tBgpPeerGroupInheritance,
        tBgpPeerGroupImportPolicy1,
        tBgpPeerGroupImportPolicy2,
        tBgpPeerGroupImportPolicy3,
        tBgpPeerGroupImportPolicy4,
        tBgpPeerGroupImportPolicy5,
        tBgpPeerGroupExportPolicy1,
        tBgpPeerGroupExportPolicy2,
        tBgpPeerGroupExportPolicy3,
        tBgpPeerGroupExportPolicy4,
        tBgpPeerGroupExportPolicy5,
        tBgpPeerGroupOperStatus,
        tBgpPeerGroupLocalASPrivate,
        tBgpPeerGroupMd5Auth,
        tBgpPeerGroupMd5AuthKey,
        tBgpPeerGroupClusterId,
        tBgpPeerGroupDisableClientReflect,
        tBgpPeerGroupGracefulRestart,
        tBgpPeerGroupGRRestartTime,
        tBgpPeerGroupGRStaleRoute,
        tBgpPeerGroupGRAdminState,
        tBgpPeerGroupGROperState,
        tBgpPeerGroupFamily,
        tBgpPeerGroupVpnApplyImport,
        tBgpPeerGroupVpnApplyExport,
        tBgpPeerGroupASOverride,
        tBgpPeerGroupOrf,
        tBgpPeerGroupExtCommsOrf,
        tBgpPeerGroupExtCommsSendOrf,
        tBgpPeerGroupExtCommsRecvOrf,
        tBgpPGSendOrfRTRowStatus
    }
    STATUS      obsolete
    DESCRIPTION
        "The group of objects supporting management of extended BGP Peer Groups
         on Nokia SROS series systems."
    ::= { tmnxBgpGroups 24 }

tmnxBgpNotificationV4v0Group     NOTIFICATION-GROUP
    NOTIFICATIONS {
        tBgpMaxNgPrefix90,
        tBgpMaxNgPrefix100,
        tBgpPeerNgGRStatusChange
    }
    STATUS      obsolete
    DESCRIPTION
        "The group of notifications supporting management of extended BGP on
         Nokia SROS series systems."
    ::= { tmnxBgpGroups 25 }

tmnxBgpObsoleteNotificationV4v0Group NOTIFICATION-GROUP
    NOTIFICATIONS {
        tBgpMaxPrefix90,
        tBgpMaxPrefix100,
        tBgpPeerGRStatusChange
    }
    STATUS      current
    DESCRIPTION
        "The group of notifications supporting management of extended BGP on
         Nokia SROS series systems."
    ::= { tmnxBgpGroups 26 }

tmnxBgpInstanceParamsV4v0Group   OBJECT-GROUP
    OBJECTS     {
        tBgpInstanceDisableFEFailover,
        tBgpInstanceDisableComms,
        tBgpInstanceDisableExtComms,
        tBgpInstanceDefaultOriginate,
        tBgpInstanceAdvertiseInactiveRts,
        tBgpInstancePeerTracking
    }
    STATUS      obsolete
    DESCRIPTION
        "The group of objects supporting management of each extended BGP
         instance parameters on Nokia SROS series systems."
    ::= { tmnxBgpGroups 27 }

tmnxBgpPeerV5v0Group             OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgMinASOrigination,
        tBgpPeerNgDampening,
        tBgpPeerNgLocalAddress,
        tBgpPeerNgLocalAddressType,
        tBgpPeerNgLocalAS,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerAS,
        tBgpPeerNgPeerType,
        tBgpPeerNgPreference,
        tBgpPeerNgRemovePrivateAS,
        tBgpPeerNgLastChanged,
        tBgpPeerNgInheritance,
        tBgpPeerNgImportPolicy1,
        tBgpPeerNgImportPolicy2,
        tBgpPeerNgImportPolicy3,
        tBgpPeerNgImportPolicy4,
        tBgpPeerNgImportPolicy5,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs
    }
    STATUS      obsolete
    DESCRIPTION
        "The group of objects supporting management of extended BGP peers on
         Nokia SROS series systems."
    ::= { tmnxBgpGroups 28 }

tmnxBgpObsoleteV5v0Group         OBJECT-GROUP
    OBJECTS     {
        tBgpPeerPeerGroup,
        tBgpPeerRowStatus,
        tBgpPeerShutdown,
        tBgpPeerDescription,
        tBgpPeerConnectRetry,
        tBgpPeerHoldTime,
        tBgpPeerKeepAlive,
        tBgpPeerMinASOrigination,
        tBgpPeerDampening,
        tBgpPeerLocalAddress,
        tBgpPeerLocalAS,
        tBgpPeerLocalPreference,
        tBgpPeerLoopDetect,
        tBgpPeerMinRouteAdvertisement,
        tBgpPeerMaxPrefix,
        tBgpPeerMEDSource,
        tBgpPeerMEDValue,
        tBgpPeerMultihop,
        tBgpPeerNextHopSelf,
        tBgpPeerNoAggregatorID,
        tBgpPeerPassive,
        tBgpPeerPeerAS,
        tBgpPeerPeerType,
        tBgpPeerPreference,
        tBgpPeerRemovePrivateAS,
        tBgpPeerLastChanged,
        tBgpPeerInheritance,
        tBgpPeerImportPolicy1,
        tBgpPeerImportPolicy2,
        tBgpPeerImportPolicy3,
        tBgpPeerImportPolicy4,
        tBgpPeerImportPolicy5,
        tBgpPeerExportPolicy1,
        tBgpPeerExportPolicy2,
        tBgpPeerExportPolicy3,
        tBgpPeerExportPolicy4,
        tBgpPeerExportPolicy5,
        tBgpPeerOperStatus,
        tBgpPeerLocalASPrivate,
        tBgpPeerMd5Auth,
        tBgpPeerMd5AuthKey,
        tBgpPeerClusterId,
        tBgpPeerDisableClientReflect,
        tBgpPeerGracefulRestart,
        tBgpPeerGRRestartTime,
        tBgpPeerGRStaleRoute,
        tBgpPeerGRAdminState,
        tBgpPeerGROperState,
        tBgpPeerFamily,
        tBgpPeerVpnRemoteFamily,
        tBgpPeerVpnApplyImport,
        tBgpPeerVpnApplyExport,
        tBgpPeerVpnLocalCaps,
        tBgpPeerVpnRemoteCaps,
        tBgpPeerConnState,
        tBgpPeerASOverride,
        tBgpPeerOrf,
        tBgpPeerExtCommsOrf,
        tBgpPeerExtCommsSendOrf,
        tBgpPeerExtCommsRecvOrf,
        tBgpPeerOperMsgOctetsRcvd,
        tBgpPeerOperMsgOctetsSent,
        tBgpPeerOperInputQueueMessages,
        tBgpPeerOperOutputQueueMessages,
        tBgpPeerOperReceivedPrefixes,
        tBgpPeerOperSentPrefixes,
        tBgpPeerOperActivePrefixes,
        tBgpPeerOperReceivedPaths,
        tBgpPeerOperPathsSuppressedByDamping,
        tBgpPeerOperFlaps,
        tBgpPeerOperLastState,
        tBgpPeerOperLastEvent,
        tBgpPeerOperVpnReceivedPrefixes,
        tBgpPeerOperVpnSentPrefixes,
        tBgpPeerOperVpnActivePrefixes,
        tBgpPeerSendOrfRTRowStatus,
        tBgpPeerOperGRSupport,
        tBgpPeerOperGRFamilyRestart,
        tBgpPeerOperGRFamilyFwding,
        tBgpPeerOperGRFamilyNegotiated,
        tBgpPeerOperGRRecvEOR,
        tBgpPeerOperGRSendEOR,
        tBgpPeerOperGRStaleRoutesTime,
        tBgpPeerOperGRRequestRestartTime,
        tBgpPeerOperGRStatus,
        tBgpPeerOperNumRestarts,
        tBgpPeerOperLastRestartTime,
        tBgpPeerOperV6ReceivedPrefixes,
        tBgpPeerOperV6SentPrefixes,
        tBgpPeerOperV6ActivePrefixes,
        tBgpPeerOperV6ReceivedPaths,
        tBgpPeerOperV6SuppPathsDamping,
        tBgpPeerOperVpnReceivedPaths,
        tBgpPeerParamsInheritance,
        tBgpPeerDisableFEFailover,
        tBgpPeerDisableComms,
        tBgpPeerDisableExtComms,
        tBgpPeerDefaultOriginate,
        tBgpPeerAdvertiseInactiveRts,
        tBgpPeerMinTTLValue,
        tBgpPeerTTLLogId,
        tBgpPeerGroupLocalAddress,
        tBgpPeerNgOperPathsSupByDamping,
        tBgpPeerNgOperV6ReceivedPaths,
        tBgpPeerNgOperV6SuppPathsDamping,
        tBgpPeerNgOperVpnReceivedPaths
    }
    STATUS      current
    DESCRIPTION
        "The group of objects supporting management of extended BGP peers on
         Nokia SROS series systems."
    ::= { tmnxBgpGroups 29 }

tmnxBgpPeerParamsV5v0Group       OBJECT-GROUP
    OBJECTS     {
        tBgpPeerNgParamsInheritance,
        tBgpPeerNgDisableFEFailover,
        tBgpPeerNgDisableComms,
        tBgpPeerNgDisableExtComms,
        tBgpPeerNgDefaultOriginate,
        tBgpPeerNgAdvertiseInactiveRts,
        tBgpPeerNgMinTTLValue,
        tBgpPeerNgTracking,
        tBgpPeerNgAdvLabelAddrFamily,
        tBgpPeerNgAuthKeyChain,
        tBgpPeerNgLastError
    }
    STATUS      obsolete
    DESCRIPTION
        "The group of objects supporting management of extended BGP peer
         parameters on Nokia SROS series systems. This group was obsoleted in
         release 14.0R4"
    ::= { tmnxBgpGroups 30 }

tmnxBgpInstanceParamsV5v0Group   OBJECT-GROUP
    OBJECTS     {
        tBgpInstanceDisableFEFailover,
        tBgpInstanceDisableComms,
        tBgpInstanceDisableExtComms,
        tBgpInstanceDefaultOriginate,
        tBgpInstanceAdvertiseInactiveRts,
        tBgpInstancePeerTracking,
        tBgpInstanceAuthKeyChain
    }
    STATUS      current
    DESCRIPTION
        "The group of objects supporting management of each extended BGP
         instance parameters on Nokia SROS series systems."
    ::= { tmnxBgpGroups 31 }

tmnxBgpPeerGroupParamsV5v0Group  OBJECT-GROUP
    OBJECTS     {
        tBgpPGParamsInheritance,
        tBgpPGDisableFEFailover,
        tBgpPGDisableComms,
        tBgpPGDisableExtComms,
        tBgpPGDefaultOriginate,
        tBgpPGAdvertiseInactiveRts,
        tBgpPGMinTTLValue,
        tBgpPGTTLLogId,
        tBgpPGLocalAddressType,
        tBgpPGLocalAddress,
        tBgpPGPeerTracking,
        tBgpPGAuthKeyChain
    }
    STATUS      current
    DESCRIPTION
        "The group of objects supporting management of extended BGP Peer Group
         parameters on Nokia SROS series systems."
    ::= { tmnxBgpGroups 32 }

tmnxBgpNotificationV5v0Group     NOTIFICATION-GROUP
    NOTIFICATIONS {
        tBgpMaxNgPrefix90,
        tBgpMaxNgPrefix100,
        tBgpPeerNgGRStatusChange,
        tBgpNgEstablished,
        tBgpNgBackwardTransition
    }
    STATUS      obsolete
    DESCRIPTION
        "the group of notifications supporting management of extended BGP on
         Nokia SROS series systems."
    ::= { tmnxBgpGroups 33 }

tmnxBgpInstanceParamsV6v0Group   OBJECT-GROUP
    OBJECTS     {
        tBgpInstanceRapidWithdrawal,
        tBgpInstanceBfdEnabled,
        tBgpInstancePurgeTimer
    }
    STATUS      current
    DESCRIPTION
        "The group of objects supporting management of each extended BGP
         instance parameters on Nokia SROS series systems release 6.0"
    ::= { tmnxBgpGroups 34 }

tmnxBgpPeerGroupParamsV6v0Group  OBJECT-GROUP
    OBJECTS     {
        tBgpPGBfdEnabled
    }
    STATUS      current
    DESCRIPTION
        "The group of objects supporting management of extended BGP Peer Group
         parameters on Nokia SROS series systems release 6.0."
    ::= { tmnxBgpGroups 35 }

tmnxBgpPeerParamsV6v0Group       OBJECT-GROUP
    OBJECTS     {
        tBgpPeerNgBfdEnabled
    }
    STATUS      current
    DESCRIPTION
        "The group of objects supporting management of extended BGP peer
         parameters on Nokia SROS series systems release 6.0."
    ::= { tmnxBgpGroups 36 }

tmnxBgpPeerV6v0Group             OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgMinASOrigination,
        tBgpPeerNgDampening,
        tBgpPeerNgLocalAddress,
        tBgpPeerNgLocalAddressType,
        tBgpPeerNgLocalAS,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerAS,
        tBgpPeerNgPeerType,
        tBgpPeerNgPreference,
        tBgpPeerNgRemovePrivateAS,
        tBgpPeerNgLastChanged,
        tBgpPeerNgInheritance,
        tBgpPeerNgImportPolicy1,
        tBgpPeerNgImportPolicy2,
        tBgpPeerNgImportPolicy3,
        tBgpPeerNgImportPolicy4,
        tBgpPeerNgImportPolicy5,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs,
        tBgpPeerNgOperVpnIpv6RecvPfxs,
        tBgpPeerNgOperVpnIpv6SentPfxs,
        tBgpPeerNgOperVpnIpv6ActivePfxs,
        tBgpPeerNgOperVpnIpv6SuppPfxDamp
    }
    STATUS      obsolete
    DESCRIPTION
        "The group of objects supporting management of extended BGP peers on
         Nokia SROS series systems."
    ::= { tmnxBgpGroups 37 }

tmnxBgpPeeringPolicyV7v0Group    OBJECT-GROUP
    OBJECTS     {
        tBgpPeeringPolicyTableLastChngd,
        tBgpPrngPlcyRowStatus,
        tBgpPrngPlcyLastChngd,
        tBgpPrngPlcyDescription,
        tBgpPrngPlcyInheritance,
        tBgpPrngPlcyAdvertiseInactiveRts,
        tBgpPrngPlcyNoAggregatorID,
        tBgpPrngPlcyASOverride,
        tBgpPrngPlcyAuthKeyChain,
        tBgpPrngPlcyMd5Auth,
        tBgpPrngPlcyMd5AuthKey,
        tBgpPrngPlcyClusterId,
        tBgpPrngPlcyConnectRetry,
        tBgpPrngPlcyDampening,
        tBgpPrngPlcyDisableClientReflect,
        tBgpPrngPlcyDisableComms,
        tBgpPrngPlcyDisableExtComms,
        tBgpPrngPlcyDisableFEFailover,
        tBgpPrngPlcyImportPolicy1,
        tBgpPrngPlcyImportPolicy2,
        tBgpPrngPlcyImportPolicy3,
        tBgpPrngPlcyImportPolicy4,
        tBgpPrngPlcyImportPolicy5,
        tBgpPrngPlcyExportPolicy1,
        tBgpPrngPlcyExportPolicy2,
        tBgpPrngPlcyExportPolicy3,
        tBgpPrngPlcyExportPolicy4,
        tBgpPrngPlcyExportPolicy5,
        tBgpPrngPlcyHoldTime,
        tBgpPrngPlcyKeepAlive,
        tBgpPrngPlcyLocalAddressType,
        tBgpPrngPlcyLocalAddress,
        tBgpPrngPlcyLocalAS,
        tBgpPrngPlcyLocalASPrivate,
        tBgpPrngPlcyLocalPreference,
        tBgpPrngPlcyLoopDetect,
        tBgpPrngPlcyMEDSource,
        tBgpPrngPlcyMEDValue,
        tBgpPrngPlcyMinASOrigination,
        tBgpPrngPlcyMinRteAdvertisement,
        tBgpPrngPlcyMultihop,
        tBgpPrngPlcyNextHopSelf,
        tBgpPrngPlcyPassive,
        tBgpPrngPlcyPeerAS,
        tBgpPrngPlcyPreference,
        tBgpPrngPlcyMaxPrefix,
        tBgpPrngPlcyRemovePrivateAS,
        tBgpPrngPlcyMinTTLValue,
        tBgpPrngPlcyPeerType,
        tBgpPeerGroupDynamicPeerGroup,
        tBgpPrngPlcyDisable4ByteASN,
        tBgpPrngPlcyRemovePrivateASLmtd
    }
    STATUS      obsolete
    DESCRIPTION
        "The group of objects supporting management of BGP peering policies on
         Nokia SROS series systems."
    ::= { tmnxBgpGroups 38 }

tmnxBgp4ByteASNV7v0Group         OBJECT-GROUP
    OBJECTS     {
        tbgp4PathAttrASPathSegment,
        tbgp4PathAttrAggregatorAS,
        tBgpConfederation4BytTblLstChngd,
        tBgpConfederation4ByteRowStatus
    }
    STATUS      current
    DESCRIPTION
        "The group of objects supporting 4-byte Autonomous System Number on
         Nokia SROS series systems release 7.0."
    ::= { tmnxBgpGroups 39 }

tmnxBgpInstanceV7v0Group         OBJECT-GROUP
    OBJECTS     {
        tBgpInstanceTableLastChanged,
        tBgpInstanceRowStatus,
        tBgpInstanceShutdown,
        tBgpInstanceDescription,
        tBgpInstanceAlwaysCompareMED,
        tBgpInstanceBgpId,
        tBgpInstanceConnectRetry,
        tBgpInstanceHoldTime,
        tBgpInstanceKeepAlive,
        tBgpInstanceMinASOrigination,
        tBgpInstanceDampening,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceImportPolicy1,
        tBgpInstanceImportPolicy2,
        tBgpInstanceImportPolicy3,
        tBgpInstanceImportPolicy4,
        tBgpInstanceImportPolicy5,
        tBgpInstanceExportPolicy1,
        tBgpInstanceExportPolicy2,
        tBgpInstanceExportPolicy3,
        tBgpInstanceExportPolicy4,
        tBgpInstanceExportPolicy5,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceIgpShortcut,
        tBgpInstanceDisallowIgp,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn,
        tBgpInstanceLocalAS4Byte,
        tBgpInstanceConfederationAS4Byte,
        tBgpInstanceDisable4ByteASN,
        tBgpInstanceMultipathEiBgpState,
        tBgpInstanceHoldTimeIsStrict,
        tBgpInstanceRemovePrivateASLmtd
    }
    STATUS      obsolete
    DESCRIPTION
        "The group of objects supporting management of each extended BGP
         instance on Nokia SROS series systems."
    ::= { tmnxBgpGroups 40 }

tmnxBgpPeerGroupV7v0Group        OBJECT-GROUP
    OBJECTS     {
        tBgpPeerGroupTableLastChanged,
        tBgpPeerGroupTableSpinlock,
        tBgpPeerGroupName,
        tBgpPeerGroupRowStatus,
        tBgpPeerGroupShutdown,
        tBgpPeerGroupDescription,
        tBgpPeerGroupConnectRetry,
        tBgpPeerGroupHoldTime,
        tBgpPeerGroupKeepAlive,
        tBgpPeerGroupMinASOrigination,
        tBgpPeerGroupDampening,
        tBgpPeerGroupLocalPreference,
        tBgpPeerGroupLoopDetect,
        tBgpPeerGroupMinRouteAdvertisement,
        tBgpPeerGroupMaxPrefix,
        tBgpPeerGroupMEDSource,
        tBgpPeerGroupMEDValue,
        tBgpPeerGroupMultihop,
        tBgpPeerGroupNextHopSelf,
        tBgpPeerGroupNoAggregatorID,
        tBgpPeerGroupPassive,
        tBgpPeerGroupPeerType,
        tBgpPeerGroupPreference,
        tBgpPeerGroupRemovePrivateAS,
        tBgpPeerGroupLastChanged,
        tBgpPeerGroupInheritance,
        tBgpPeerGroupImportPolicy1,
        tBgpPeerGroupImportPolicy2,
        tBgpPeerGroupImportPolicy3,
        tBgpPeerGroupImportPolicy4,
        tBgpPeerGroupImportPolicy5,
        tBgpPeerGroupExportPolicy1,
        tBgpPeerGroupExportPolicy2,
        tBgpPeerGroupExportPolicy3,
        tBgpPeerGroupExportPolicy4,
        tBgpPeerGroupExportPolicy5,
        tBgpPeerGroupOperStatus,
        tBgpPeerGroupLocalASPrivate,
        tBgpPeerGroupMd5Auth,
        tBgpPeerGroupMd5AuthKey,
        tBgpPeerGroupClusterId,
        tBgpPeerGroupDisableClientReflect,
        tBgpPeerGroupGracefulRestart,
        tBgpPeerGroupGRRestartTime,
        tBgpPeerGroupGRStaleRoute,
        tBgpPeerGroupGRAdminState,
        tBgpPeerGroupGROperState,
        tBgpPeerGroupFamily,
        tBgpPeerGroupVpnApplyImport,
        tBgpPeerGroupVpnApplyExport,
        tBgpPeerGroupASOverride,
        tBgpPeerGroupOrf,
        tBgpPeerGroupExtCommsOrf,
        tBgpPeerGroupExtCommsSendOrf,
        tBgpPeerGroupExtCommsRecvOrf,
        tBgpPGSendOrfRTRowStatus,
        tBgpPeerGroupLocalAS4Byte,
        tBgpPeerGroupPeerAS4Byte,
        tBgpPeerGroupDisable4ByteASN,
        tBgpPeerGroupHoldTimeIsStrict,
        tBgpPeerGroupRemovePrivateASLmtd
    }
    STATUS      obsolete
    DESCRIPTION
        "The group of objects supporting management of extended BGP Peer Groups
         on Nokia SROS series systems."
    ::= { tmnxBgpGroups 41 }

tmnxBgpPeerV7v0Group             OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgMinASOrigination,
        tBgpPeerNgDampening,
        tBgpPeerNgLocalAddress,
        tBgpPeerNgLocalAddressType,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerType,
        tBgpPeerNgPreference,
        tBgpPeerNgRemovePrivateAS,
        tBgpPeerNgLastChanged,
        tBgpPeerNgInheritance,
        tBgpPeerNgImportPolicy1,
        tBgpPeerNgImportPolicy2,
        tBgpPeerNgImportPolicy3,
        tBgpPeerNgImportPolicy4,
        tBgpPeerNgImportPolicy5,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs,
        tBgpPeerNgOperVpnIpv6RecvPfxs,
        tBgpPeerNgOperVpnIpv6SentPfxs,
        tBgpPeerNgOperVpnIpv6ActivePfxs,
        tBgpPeerNgOperVpnIpv6SuppPfxDamp,
        tBgpPeerNgLocalAS4Byte,
        tBgpPeerNgPeerAS4Byte,
        tBgpPeerNgDisable4ByteASN,
        tBgpPeerNgOperMvpnV4SuppPfxDamp,
        tBgpPeerNgOperMvpnV4RecvPfxs,
        tBgpPeerNgOperMvpnV4SentPfxs,
        tBgpPeerNgOperMvpnV4ActivePfxs,
        tBgpPeerNgHoldTimeIsStrict,
        tBgpPeerNgL2vpnCiscoInterop,
        tBgpPeerNgRemovePrivateASLmtd
    }
    STATUS      obsolete
    DESCRIPTION
        "The group of objects supporting management of extended BGP peers on
         Nokia SROS series systems."
    ::= { tmnxBgpGroups 42 }

tmnxBgpObsoleteV7v0Group         OBJECT-GROUP
    OBJECTS     {
        tBgpInstanceLocalAS,
        tBgpInstanceConfederationAS,
        tBgpPeerGroupLocalAS,
        tBgpPeerGroupPeerAS,
        tBgpPeerNgLocalAS,
        tBgpPeerNgPeerAS,
        tBgpConfederationTableLastChanged,
        tBgpConfederationRowStatus
    }
    STATUS      current
    DESCRIPTION
        "The group of objects in TIMETRA-BGP-MIB which are obsoleted in Nokia
         SROS 7.0 series systems."
    ::= { tmnxBgpGroups 43 }

tmnxBgpNotifyObjsV7v0Group       OBJECT-GROUP
    OBJECTS     {
        tBgpPeerNgAddrType,
        tBgpPeerNgAddr,
        tBgpRouteInvalidReason,
        tBgpRouteNLRI
    }
    STATUS      current
    DESCRIPTION
        "The group of notify objects supporting management of extended BGP on
         Nokia SROS series systems release 7.0."
    ::= { tmnxBgpGroups 44 }

tmnxBgpNotificationV7v0Group     NOTIFICATION-GROUP
    NOTIFICATIONS {
        tBgpPeerNgHoldTimeInconsistent,
        tBgp4RouteInvalid
    }
    STATUS      current
    DESCRIPTION
        "The group of notifications supporting management of extended BGP on
         Nokia SROS series systems release 7.0."
    ::= { tmnxBgpGroups 45 }

tmnxBgpInstanceV8v0Group         OBJECT-GROUP
    OBJECTS     {
        tBgpInstanceRapidUpdate,
        tBgpInstanceAsPathIgnoreFamily
    }
    STATUS      current
    DESCRIPTION
        "The group of objects supporting management of each extended BGP
         instance on Nokia SROS series systems release 8.0"
    ::= { tmnxBgpGroups 46 }

tmnxBgpObsoleteV8v0Group         OBJECT-GROUP
    OBJECTS     {
        tBgpInstanceAsPathIgnore
    }
    STATUS      current
    DESCRIPTION
        "The group of objects in TIMETRA-BGP-MIB which are obsoleted in Nokia
         SROS 8.0 series systems."
    ::= { tmnxBgpGroups 47 }

tmnxBgpPeerV8v0Group             OBJECT-GROUP
    OBJECTS     {
        tBgpPeerNgOperMvpnV4ActivePfxs,
        tBgpPeerNgOperl2VpnSuppPfxDamp,
        tBgpPeerNgOperl2VpnRecvPfxs,
        tBgpPeerNgOperl2VpnSentPfxs,
        tBgpPeerNgOperl2VpnActivePfxs,
        tBgpPeerNgOperMdtSafiSuppPfxDamp,
        tBgpPeerNgOperMdtSafiRecvPfxs,
        tBgpPeerNgOperMdtSafiSentPfxs,
        tBgpPeerNgOperMdtSafiActivePfxs
    }
    STATUS      current
    DESCRIPTION
        "The group of objects supporting management of extended BGP peers on
         Nokia 8.0 SROS series systems."
    ::= { tmnxBgpGroups 48 }

tmnxBgpGlobalV8v0Group           OBJECT-GROUP
    OBJECTS     {
        tBgpInstancePMTUDiscovery,
        tBgpPeerGroupPMTUDiscovery,
        tBgpPeerNgPMTUDiscovery,
        tBgpPeerNgAdvertiseLdpPrefix,
        tBgpPeerGroupMaxPrefixLogOnly,
        tBgpPeerGroupMaxPrefixThreshold,
        tBgpPeerNgMaxPrefixLogOnly,
        tBgpPeerNgMaxPrefixThreshold,
        tBgpPrngPlcyMaxPrefixLogOnly,
        tBgpPrngPlcyMaxPrefixThreshold
    }
    STATUS      obsolete
    DESCRIPTION
        "The group of objects supporting management of extended BGP on Nokia
         SROS series systems release 8.0."
    ::= { tmnxBgpGroups 49 }

tmnxBgpAddPathV9v0R4Group        OBJECT-GROUP
    OBJECTS     {
        tBgpInstanceEnableAddPath,
        tBgpInstanceRecvAddPath,
        tBgpInstanceIpv4AddPathLimit,
        tBgpInstanceVpnIpv4AddPathLimit,
        tBgpInstanceIpv6AddPathLimit,
        tBgpInstanceVpnIpv6AddPathLimit,
        tBgpPGEnableAddPath,
        tBgpPGRecvAddPath,
        tBgpPGIpv4AddPathLimit,
        tBgpPGVpnIpv4AddPathLimit,
        tBgpPGIpv6AddPathLimit,
        tBgpPGVpnIpv6AddPathLimit,
        tBgpPeerNgEnableAddPath,
        tBgpPeerNgRecvAddPath,
        tBgpPeerNgIpv4AddPathLimit,
        tBgpPeerNgVpnIpv4AddPathLimit,
        tBgpPeerNgIpv6AddPathLimit,
        tBgpPeerNgVpnIpv6AddPathLimit,
        tBgpPeerNgAddPathSendRemoteCaps,
        tBgpPeerNgAddPathRecvRemoteCaps,
        tBgpPeerNgOperBackupPrefixes,
        tBgpPeerNgOperV6BackupPrefixes
    }
    STATUS      obsolete
    DESCRIPTION
        "The group of objects supporting BGP ADD-PATH on Nokia SROS series
         systems release 9.0R4."
    ::= { tmnxBgpGroups 50 }

tmnxBgpPeerV9v0Group             OBJECT-GROUP
    OBJECTS     {
        tBgpPeerNgOperMsPwSuppPfxDamp,
        tBgpPeerNgOperMsPwRecvPfxs,
        tBgpPeerNgOperMsPwSentPfxs,
        tBgpPeerNgOperMsPwActivePfxs,
        tBgpPeerNgOperFlowIpv4SupPfxDamp,
        tBgpPeerNgOperFlowIpv4RecvPfxs,
        tBgpPeerNgOperFlowIpv4SentPfxs,
        tBgpPeerNgOperFlowIpv4ActivePfxs
    }
    STATUS      current
    DESCRIPTION
        "The group of objects supporting management of extended BGP peers on
         Nokia 9.0 SROS series systems."
    ::= { tmnxBgpGroups 51 }

tmnxBgpGlobalV9v0Group           OBJECT-GROUP
    OBJECTS     {
        tBgpInstanceTransportTunnel,
        tBgpInstanceAdvertiseExternal,
        tBgpInstanceBackupPath,
        tBgpPGUpdatedErrorHandling,
        tBgpPeerNgUpdatedErrorHandling,
        tBgpInstanceDisableRtTblInstall
    }
    STATUS      obsolete
    DESCRIPTION
        "The group of objects supporting management of extended BGP on Nokia
         SROS series systems release 9.0."
    ::= { tmnxBgpGroups 52 }

tmnxBgpFlowSpecV9v0Group         OBJECT-GROUP
    OBJECTS     {
        tBgpPGFlowspecValidate,
        tBgpPeerNgFlowspecValidate,
        tBgpInstanceFlowspecValidate
    }
    STATUS      obsolete
    DESCRIPTION
        "The group of objects supporting BGP Flowspec on Nokia SROS series
         systems release 9.0."
    ::= { tmnxBgpGroups 53 }

tmnxBgpDisableCapNegoV9v0Group   OBJECT-GROUP
    OBJECTS     {
        tBgpPeerGroupDisableCapNego,
        tBgpPeerNgDisableCapNegotiation
    }
    STATUS      current
    DESCRIPTION
        "The group of objects supporting disabling capability negotiation on
         BGP Group and peer level on Nokia SROS series systems release 9.0."
    ::= { tmnxBgpGroups 54 }

tmnxBgpNotifyObjsV9v0Group       OBJECT-GROUP
    OBJECTS     {
        tBgpFlowspecExtCommunityAction,
        tBgpFlowspecExtCommActionValue,
        tBgpPeerFlowRouteDestAddrType,
        tBgpPeerFlowRouteDestAddr,
        tBgpFlowRouteInvalidReason,
        tBgpFlowRouteNLRI,
        tBgp4OptTransPathAttrType,
        tBgp4OptTransPathAttrLength,
        tBgp4OptTransPathAttribute,
        tBgp4OTWithdrawnRouteLength,
        tBgp4OTWithdrawnRoutePrefix
    }
    STATUS      obsolete
    DESCRIPTION
        "The group of notify objects supporting management of extended BGP on
         Nokia SROS series systems release 9.0."
    ::= { tmnxBgpGroups 55 }

tmnxBgpNotificationV9v0Group     NOTIFICATION-GROUP
    NOTIFICATIONS {
        tBgpMaxNgPrefix100,
        tBgpPeerNgGRStatusChange,
        tBgpNgEstablished,
        tBgpNgBackwardTransition,
        tBgpFlowspecUnsupportdComAction,
        tBgpFlowRouteInvalid,
        tBgpMaxNgPrefixThreshReached,
        tBgp4OptTransPathAttrInvalid,
        tBgp4OptTransWithdrawnRoutes
    }
    STATUS      obsolete
    DESCRIPTION
        "The group of notifications supporting management of extended BGP on
         Nokia SROS series systems release 9.0."
    ::= { tmnxBgpGroups 56 }

tmnxBgpGlobalV10v0Group          OBJECT-GROUP
    OBJECTS     {
        tBgpInstanceIgnoreNextHopMetric,
        tBgpInstanceMpBgpKeep,
        tBgpInstanceIgnoreRouterId,
        tBgpInstanceAlwaysCompMEDStrict,
        tBgpPGAigp,
        tBgpPeerNgAigp,
        tBgpPeerNgOperVpnV4BackupPfxs,
        tBgpPeerNgOperVpnV6BackupPfxs,
        tBgpInstanceMinHoldTime,
        tBgpPGMinHoldTime,
        tBgpPeerNgMinHoldTime,
        tBgpPeerNgSplitHorizon,
        tBgpInstRemovePrivateSkipPeerAs,
        tBgpPGRemovePrivateSkipPeerAs,
        tBgpPeerNgRemPrivateSkipPeerAs,
        tBgpInstanceNHResUseBgpRoutes,
        tBgpPeerNgOperMcastVpnV4RecvPfxs,
        tBgpPeerNgOperMcastVpnV4SentPfxs,
        tBgpPeerNgOperMcastVpnV4ActPfxs
    }
    STATUS      current
    DESCRIPTION
        "The group of objects supporting management of extended BGP on Nokia
         SROS series systems release 10.0."
    ::= { tmnxBgpGroups 57 }

tmnxBgpRTConstraintV10v0Group    OBJECT-GROUP
    OBJECTS     {
        tBgpPGDefaultRouteTarget,
        tBgpPeerNgDefaultRouteTarget,
        tBgpPeerNgOperRtTgtSuppPfxDamp,
        tBgpPeerNgOperRtTgtRecvPfxs,
        tBgpPeerNgOperRtTgtSentPfxs,
        tBgpPeerNgOperRtTgtActivePfxs
    }
    STATUS      current
    DESCRIPTION
        "The group of objects supporting Route Target Constraint on Nokia SROS
         series systems release 10.0."
    ::= { tmnxBgpGroups 58 }

tmnxBgpInstanceV10v0Group        OBJECT-GROUP
    OBJECTS     {
        tBgpInstanceTableLastChanged,
        tBgpInstanceRowStatus,
        tBgpInstanceShutdown,
        tBgpInstanceDescription,
        tBgpInstanceAlwaysCompareMED,
        tBgpInstanceBgpId,
        tBgpInstanceConnectRetry,
        tBgpInstanceHoldTime,
        tBgpInstanceKeepAlive,
        tBgpInstanceMinASOrigination,
        tBgpInstanceDampening,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceIgpShortcut,
        tBgpInstanceDisallowIgp,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn,
        tBgpInstanceLocalAS4Byte,
        tBgpInstanceConfederationAS4Byte,
        tBgpInstanceDisable4ByteASN,
        tBgpInstanceMultipathEiBgpState,
        tBgpInstanceRemovePrivateASLmtd,
        tBgpInstancePlcyImportPolicy1,
        tBgpInstancePlcyImportPolicy2,
        tBgpInstancePlcyImportPolicy3,
        tBgpInstancePlcyImportPolicy4,
        tBgpInstancePlcyImportPolicy5,
        tBgpInstancePlcyImportPolicy6,
        tBgpInstancePlcyImportPolicy7,
        tBgpInstancePlcyImportPolicy8,
        tBgpInstancePlcyImportPolicy9,
        tBgpInstancePlcyImportPolicy10,
        tBgpInstancePlcyImportPolicy11,
        tBgpInstancePlcyImportPolicy12,
        tBgpInstancePlcyImportPolicy13,
        tBgpInstancePlcyImportPolicy14,
        tBgpInstancePlcyImportPolicy15,
        tBgpInstancePlcyExportPolicy1,
        tBgpInstancePlcyExportPolicy2,
        tBgpInstancePlcyExportPolicy3,
        tBgpInstancePlcyExportPolicy4,
        tBgpInstancePlcyExportPolicy5,
        tBgpInstancePlcyExportPolicy6,
        tBgpInstancePlcyExportPolicy7,
        tBgpInstancePlcyExportPolicy8,
        tBgpInstancePlcyExportPolicy9,
        tBgpInstancePlcyExportPolicy10,
        tBgpInstancePlcyExportPolicy11,
        tBgpInstancePlcyExportPolicy12,
        tBgpInstancePlcyExportPolicy13,
        tBgpInstancePlcyExportPolicy14,
        tBgpInstancePlcyExportPolicy15
    }
    STATUS      obsolete
    DESCRIPTION
        "The group of objects supporting management of each extended BGP
         instance on Nokia SROS series systems since release 10.0."
    ::= { tmnxBgpGroups 59 }

tmnxBgpPeerGroupV10v0Group       OBJECT-GROUP
    OBJECTS     {
        tBgpPeerGroupTableLastChanged,
        tBgpPeerGroupTableSpinlock,
        tBgpPeerGroupName,
        tBgpPeerGroupRowStatus,
        tBgpPeerGroupShutdown,
        tBgpPeerGroupDescription,
        tBgpPeerGroupConnectRetry,
        tBgpPeerGroupHoldTime,
        tBgpPeerGroupKeepAlive,
        tBgpPeerGroupMinASOrigination,
        tBgpPeerGroupDampening,
        tBgpPeerGroupLocalPreference,
        tBgpPeerGroupLoopDetect,
        tBgpPeerGroupMinRouteAdvertisement,
        tBgpPeerGroupMaxPrefix,
        tBgpPeerGroupMEDSource,
        tBgpPeerGroupMEDValue,
        tBgpPeerGroupMultihop,
        tBgpPeerGroupNextHopSelf,
        tBgpPeerGroupNoAggregatorID,
        tBgpPeerGroupPassive,
        tBgpPeerGroupPeerType,
        tBgpPeerGroupPreference,
        tBgpPeerGroupRemovePrivateAS,
        tBgpPeerGroupLastChanged,
        tBgpPeerGroupInheritance,
        tBgpPeerGroupOperStatus,
        tBgpPeerGroupLocalASPrivate,
        tBgpPeerGroupMd5Auth,
        tBgpPeerGroupMd5AuthKey,
        tBgpPeerGroupClusterId,
        tBgpPeerGroupDisableClientReflect,
        tBgpPeerGroupGracefulRestart,
        tBgpPeerGroupGRRestartTime,
        tBgpPeerGroupGRStaleRoute,
        tBgpPeerGroupGRAdminState,
        tBgpPeerGroupGROperState,
        tBgpPeerGroupFamily,
        tBgpPeerGroupVpnApplyImport,
        tBgpPeerGroupVpnApplyExport,
        tBgpPeerGroupASOverride,
        tBgpPeerGroupOrf,
        tBgpPeerGroupExtCommsOrf,
        tBgpPeerGroupExtCommsSendOrf,
        tBgpPeerGroupExtCommsRecvOrf,
        tBgpPGSendOrfRTRowStatus,
        tBgpPeerGroupLocalAS4Byte,
        tBgpPeerGroupPeerAS4Byte,
        tBgpPeerGroupDisable4ByteASN,
        tBgpPeerGroupRemovePrivateASLmtd,
        tBgpPeerGroupPlcyImportPolicy1,
        tBgpPeerGroupPlcyImportPolicy2,
        tBgpPeerGroupPlcyImportPolicy3,
        tBgpPeerGroupPlcyImportPolicy4,
        tBgpPeerGroupPlcyImportPolicy5,
        tBgpPeerGroupPlcyImportPolicy6,
        tBgpPeerGroupPlcyImportPolicy7,
        tBgpPeerGroupPlcyImportPolicy8,
        tBgpPeerGroupPlcyImportPolicy9,
        tBgpPeerGroupPlcyImportPolicy10,
        tBgpPeerGroupPlcyImportPolicy11,
        tBgpPeerGroupPlcyImportPolicy12,
        tBgpPeerGroupPlcyImportPolicy13,
        tBgpPeerGroupPlcyImportPolicy14,
        tBgpPeerGroupPlcyImportPolicy15,
        tBgpPeerGroupPlcyExportPolicy1,
        tBgpPeerGroupPlcyExportPolicy2,
        tBgpPeerGroupPlcyExportPolicy3,
        tBgpPeerGroupPlcyExportPolicy4,
        tBgpPeerGroupPlcyExportPolicy5,
        tBgpPeerGroupPlcyExportPolicy6,
        tBgpPeerGroupPlcyExportPolicy7,
        tBgpPeerGroupPlcyExportPolicy8,
        tBgpPeerGroupPlcyExportPolicy9,
        tBgpPeerGroupPlcyExportPolicy10,
        tBgpPeerGroupPlcyExportPolicy11,
        tBgpPeerGroupPlcyExportPolicy12,
        tBgpPeerGroupPlcyExportPolicy13,
        tBgpPeerGroupPlcyExportPolicy14,
        tBgpPeerGroupPlcyExportPolicy15
    }
    STATUS      obsolete
    DESCRIPTION
        "The group of objects supporting management of extended BGP Peer Groups
         on Nokia SROS series systems since release 10.0."
    ::= { tmnxBgpGroups 60 }

tmnxBgpPeerV10v0Group            OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgMinASOrigination,
        tBgpPeerNgDampening,
        tBgpPeerNgLocalAddress,
        tBgpPeerNgLocalAddressType,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerType,
        tBgpPeerNgPreference,
        tBgpPeerNgRemovePrivateAS,
        tBgpPeerNgLastChanged,
        tBgpPeerNgInheritance,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs,
        tBgpPeerNgOperVpnIpv6RecvPfxs,
        tBgpPeerNgOperVpnIpv6SentPfxs,
        tBgpPeerNgOperVpnIpv6ActivePfxs,
        tBgpPeerNgOperVpnIpv6SuppPfxDamp,
        tBgpPeerNgLocalAS4Byte,
        tBgpPeerNgPeerAS4Byte,
        tBgpPeerNgDisable4ByteASN,
        tBgpPeerNgOperMvpnV4SuppPfxDamp,
        tBgpPeerNgOperMvpnV4RecvPfxs,
        tBgpPeerNgOperMvpnV4SentPfxs,
        tBgpPeerNgOperMvpnV4ActivePfxs,
        tBgpPeerNgL2vpnCiscoInterop,
        tBgpPeerNgRemovePrivateASLmtd,
        tBgpPeerPlcyImportPolicy1,
        tBgpPeerPlcyImportPolicy2,
        tBgpPeerPlcyImportPolicy3,
        tBgpPeerPlcyImportPolicy4,
        tBgpPeerPlcyImportPolicy5,
        tBgpPeerPlcyImportPolicy6,
        tBgpPeerPlcyImportPolicy7,
        tBgpPeerPlcyImportPolicy8,
        tBgpPeerPlcyImportPolicy9,
        tBgpPeerPlcyImportPolicy10,
        tBgpPeerPlcyImportPolicy11,
        tBgpPeerPlcyImportPolicy12,
        tBgpPeerPlcyImportPolicy13,
        tBgpPeerPlcyImportPolicy14,
        tBgpPeerPlcyImportPolicy15,
        tBgpPeerPlcyExportPolicy1,
        tBgpPeerPlcyExportPolicy2,
        tBgpPeerPlcyExportPolicy3,
        tBgpPeerPlcyExportPolicy4,
        tBgpPeerPlcyExportPolicy5,
        tBgpPeerPlcyExportPolicy6,
        tBgpPeerPlcyExportPolicy7,
        tBgpPeerPlcyExportPolicy8,
        tBgpPeerPlcyExportPolicy9,
        tBgpPeerPlcyExportPolicy10,
        tBgpPeerPlcyExportPolicy11,
        tBgpPeerPlcyExportPolicy12,
        tBgpPeerPlcyExportPolicy13,
        tBgpPeerPlcyExportPolicy14,
        tBgpPeerPlcyExportPolicy15
    }
    STATUS      obsolete
    DESCRIPTION
        "The group of objects supporting management of extended BGP peers on
         Nokia SROS series systems since release 10.0."
    ::= { tmnxBgpGroups 61 }

tmnxBgpPeeringPlcyV10v0Group     OBJECT-GROUP
    OBJECTS     {
        tBgpPeeringPlcyImportPolicy1,
        tBgpPeeringPlcyImportPolicy2,
        tBgpPeeringPlcyImportPolicy3,
        tBgpPeeringPlcyImportPolicy4,
        tBgpPeeringPlcyImportPolicy5,
        tBgpPeeringPlcyImportPolicy6,
        tBgpPeeringPlcyImportPolicy7,
        tBgpPeeringPlcyImportPolicy8,
        tBgpPeeringPlcyImportPolicy9,
        tBgpPeeringPlcyImportPolicy10,
        tBgpPeeringPlcyImportPolicy11,
        tBgpPeeringPlcyImportPolicy12,
        tBgpPeeringPlcyImportPolicy13,
        tBgpPeeringPlcyImportPolicy14,
        tBgpPeeringPlcyImportPolicy15,
        tBgpPeeringPlcyExportPolicy1,
        tBgpPeeringPlcyExportPolicy2,
        tBgpPeeringPlcyExportPolicy3,
        tBgpPeeringPlcyExportPolicy4,
        tBgpPeeringPlcyExportPolicy5,
        tBgpPeeringPlcyExportPolicy6,
        tBgpPeeringPlcyExportPolicy7,
        tBgpPeeringPlcyExportPolicy8,
        tBgpPeeringPlcyExportPolicy9,
        tBgpPeeringPlcyExportPolicy10,
        tBgpPeeringPlcyExportPolicy11,
        tBgpPeeringPlcyExportPolicy12,
        tBgpPeeringPlcyExportPolicy13,
        tBgpPeeringPlcyExportPolicy14,
        tBgpPeeringPlcyExportPolicy15
    }
    STATUS      current
    DESCRIPTION
        "The group of objects supporting management of BGP peering policies on
         Nokia SROS series systems since release 10.0."
    ::= { tmnxBgpGroups 62 }

tmnxBgpPeeringPolicyV10v0Group   OBJECT-GROUP
    OBJECTS     {
        tBgpPeeringPolicyTableLastChngd,
        tBgpPrngPlcyRowStatus,
        tBgpPrngPlcyLastChngd,
        tBgpPrngPlcyDescription,
        tBgpPrngPlcyInheritance,
        tBgpPrngPlcyAdvertiseInactiveRts,
        tBgpPrngPlcyNoAggregatorID,
        tBgpPrngPlcyASOverride,
        tBgpPrngPlcyAuthKeyChain,
        tBgpPrngPlcyMd5Auth,
        tBgpPrngPlcyMd5AuthKey,
        tBgpPrngPlcyClusterId,
        tBgpPrngPlcyConnectRetry,
        tBgpPrngPlcyDampening,
        tBgpPrngPlcyDisableClientReflect,
        tBgpPrngPlcyDisableComms,
        tBgpPrngPlcyDisableExtComms,
        tBgpPrngPlcyDisableFEFailover,
        tBgpPrngPlcyHoldTime,
        tBgpPrngPlcyKeepAlive,
        tBgpPrngPlcyLocalAddressType,
        tBgpPrngPlcyLocalAddress,
        tBgpPrngPlcyLocalAS,
        tBgpPrngPlcyLocalASPrivate,
        tBgpPrngPlcyLocalPreference,
        tBgpPrngPlcyLoopDetect,
        tBgpPrngPlcyMEDSource,
        tBgpPrngPlcyMEDValue,
        tBgpPrngPlcyMinASOrigination,
        tBgpPrngPlcyMinRteAdvertisement,
        tBgpPrngPlcyMultihop,
        tBgpPrngPlcyNextHopSelf,
        tBgpPrngPlcyPassive,
        tBgpPrngPlcyPeerAS,
        tBgpPrngPlcyPreference,
        tBgpPrngPlcyMaxPrefix,
        tBgpPrngPlcyRemovePrivateAS,
        tBgpPrngPlcyMinTTLValue,
        tBgpPrngPlcyPeerType,
        tBgpPeerGroupDynamicPeerGroup,
        tBgpPrngPlcyDisable4ByteASN,
        tBgpPrngPlcyRemovePrivateASLmtd
    }
    STATUS      obsolete
    DESCRIPTION
        "The group of objects supporting management of BGP peering policies on
         Nokia SROS series systems since release 10.0."
    ::= { tmnxBgpGroups 63 }

tmnxBgpObsoleteV10v0Group        OBJECT-GROUP
    OBJECTS     {
        tBgpInstanceHoldTimeIsStrict,
        tBgpPeerGroupHoldTimeIsStrict,
        tBgpPeerNgHoldTimeIsStrict,
        tBgpInstanceImportPolicy1,
        tBgpInstanceImportPolicy2,
        tBgpInstanceImportPolicy3,
        tBgpInstanceImportPolicy4,
        tBgpInstanceImportPolicy5,
        tBgpInstanceExportPolicy1,
        tBgpInstanceExportPolicy2,
        tBgpInstanceExportPolicy3,
        tBgpInstanceExportPolicy4,
        tBgpInstanceExportPolicy5,
        tBgpPeerGroupImportPolicy1,
        tBgpPeerGroupImportPolicy2,
        tBgpPeerGroupImportPolicy3,
        tBgpPeerGroupImportPolicy4,
        tBgpPeerGroupImportPolicy5,
        tBgpPeerGroupExportPolicy1,
        tBgpPeerGroupExportPolicy2,
        tBgpPeerGroupExportPolicy3,
        tBgpPeerGroupExportPolicy4,
        tBgpPeerGroupExportPolicy5,
        tBgpPeerNgImportPolicy1,
        tBgpPeerNgImportPolicy2,
        tBgpPeerNgImportPolicy3,
        tBgpPeerNgImportPolicy4,
        tBgpPeerNgImportPolicy5,
        tBgpPeerNgExportPolicy1,
        tBgpPeerNgExportPolicy2,
        tBgpPeerNgExportPolicy3,
        tBgpPeerNgExportPolicy4,
        tBgpPeerNgExportPolicy5,
        tBgpPrngPlcyImportPolicy1,
        tBgpPrngPlcyImportPolicy2,
        tBgpPrngPlcyImportPolicy3,
        tBgpPrngPlcyImportPolicy4,
        tBgpPrngPlcyImportPolicy5,
        tBgpPrngPlcyExportPolicy1,
        tBgpPrngPlcyExportPolicy2,
        tBgpPrngPlcyExportPolicy3,
        tBgpPrngPlcyExportPolicy4,
        tBgpPrngPlcyExportPolicy5
    }
    STATUS      current
    DESCRIPTION
        "The group of objects in TIMETRA-BGP-MIB which are obsoleted in Nokia
         SROS 10.0 series systems."
    ::= { tmnxBgpGroups 64 }

tmnxBgpGlobalV11v0Group          OBJECT-GROUP
    OBJECTS     {
        tBgpInstLocalASNoPrependGlobalAS,
        tBgpPGLocalASNoPrependGlobalAS,
        tBgpPeerNgLclASNoPrependGlobalAS,
        tBgpPeerNgOperMvpnV6SuppPfxDamp,
        tBgpPeerNgOperMvpnV6RecvPfxs,
        tBgpPeerNgOperMvpnV6SentPfxs,
        tBgpPeerNgOperMvpnV6ActivePfxs,
        tBgpInstanceEnableRRVpnFwding,
        tBgpPGMaxPrefixIdleTimeOut,
        tBgpPeerNgMaxPrefixIdleTimeOut,
        tBgpPeerNgOperFlowIpv6SupPfxDamp,
        tBgpPeerNgOperFlowIpv6RecvPfxs,
        tBgpPeerNgOperFlowIpv6SentPfxs,
        tBgpPeerNgOperFlowIpv6ActivePfxs,
        tBgpInstanceNHResPolicy,
        tBgpInstancePeerTrackingPolicy,
        tBgpInstanceTransportTunnel,
        tBgpInstanceAdvertiseExternal,
        tBgpInstanceBackupPath,
        tBgpInstanceDisableRtTblInstall,
        tBgpInstanceDeterministicMED,
        tBgpInstanceSplitHorizon,
        tBgpPGSplitHorizon,
        tBgpInstanceIgnoreRtrIdInternal,
        tBgpInstanceIgnoreRtrIdExternal
    }
    STATUS      obsolete
    DESCRIPTION
        "The group of objects supporting management of extended BGP on Nokia
         SROS series systems release 11.0."
    ::= { tmnxBgpGroups 65 }

tmnxBgpPeerGroupV11v0Group       OBJECT-GROUP
    OBJECTS     {
        tBgpPeerGroupCreationOrigin
    }
    STATUS      current
    DESCRIPTION
        "The group of objects supporting management of extended BGP Peer Groups
         on Nokia SROS series systems added in release 11.0."
    ::= { tmnxBgpGroups 66 }

tmnxBgpObsoleteV11v0Group        OBJECT-GROUP
    OBJECTS     {
        tBgpPGUpdatedErrorHandling,
        tBgpPeerNgUpdatedErrorHandling,
        tBgp4OptTransPathAttrType,
        tBgp4OptTransPathAttrLength,
        tBgp4OptTransPathAttribute,
        tBgp4OTWithdrawnRouteLength,
        tBgp4OTWithdrawnRoutePrefix
    }
    STATUS      current
    DESCRIPTION
        "The group of objects in TIMETRA-BGP-MIB which are obsoleted in Nokia
         SROS 11.0 series systems."
    ::= { tmnxBgpGroups 67 }

tmnxBgpGlobalDCGroup             OBJECT-GROUP
    OBJECTS     {
        tBgpPeerNgOperEvpnSupPfxDamp,
        tBgpPeerNgOperEvpnRecvPfxs,
        tBgpPeerNgOperEvpnSentPfxs,
        tBgpPeerNgOperEvpnActivePfxs
    }
    STATUS      current
    DESCRIPTION
        "The group of objects supporting management of extended BGP on Nokia
         Data Center series systems."
    ::= { tmnxBgpGroups 68 }

tmnxBgpDPOscilationV11v0Group    OBJECT-GROUP
    OBJECTS     {
        tBgpInstGrRestartNotification,
        tBgpInstanceFaultTolerance,
        tBgpPGGRRestartNotification,
        tBgpPGFaultTolerance,
        tBgpPeerNgGRRestartNotification,
        tBgpPeerNgFaultTolerance,
        tBgpInstanceDampPeerOscillations,
        tBgpInstDmpPeerOscInitialWaitTim,
        tBgpInstDmpPeerOscSecondWaitTime,
        tBgpInstDmpPeerOscMaxWaitTime,
        tBgpInstDmpPeerOscErrorInterval,
        tBgpPGDampPeerOscillations,
        tBgpPGDampPeerOscInitialWaitTime,
        tBgpPGDampPeerOscSecondWaitTime,
        tBgpPGDampPeerOscMaxWaitTime,
        tBgpPGDampPeerOscErrorInterval,
        tBgpPeerNgDampPeerOscillations,
        tBgpPeerNgDampOscInitialWaitTime,
        tBgpPeerNgDampOscSecondWaitTime,
        tBgpPeerNgDampOscMaxWaitTime,
        tBgpPeerNgDampOscErrorInterval,
        tBgpPeerNgOperUpdateErrors,
        tBgpPeerNgOperGRNotifFamilyNego,
        tBgpPeerNgOperRemIdleHoldTime
    }
    STATUS      current
    DESCRIPTION
        "The group of objects supporting management of damping peer
         oscillations on Nokia SROS series systems added in release 11.0."
    ::= { tmnxBgpGroups 69 }

tmnxBgpNotifyObjsV11v0Group      OBJECT-GROUP
    OBJECTS     {
        tBgp4PathAttrType,
        tBgp4PathAttrLength,
        tBgp4PathAttribute,
        tBgp4WithdrawnRoutePrefix,
        tBgp4UpdateMessage,
        tBgpFlowspecExtCommunityAction,
        tBgpFlowspecExtCommActionValue,
        tBgpPeerFlowRouteDestAddrType,
        tBgpPeerFlowRouteDestAddr,
        tBgpFlowRouteInvalidReason,
        tBgpFlowRouteNLRI
    }
    STATUS      obsolete
    DESCRIPTION
        "The group of notify objects supporting management of extended BGP on
         Nokia SROS series systems release 11.0."
    ::= { tmnxBgpGroups 70 }

tmnxBgpNotificationV11v0Group    NOTIFICATION-GROUP
    NOTIFICATIONS {
        tBgp4UpdateInvalid,
        tBgp4PathAttrInvalid,
        tBgp4WithdrawnRtFromUpdateError,
        tBgpMaxNgPrefix100,
        tBgpPeerNgGRStatusChange,
        tBgpNgEstablished,
        tBgpNgBackwardTransition,
        tBgpFlowspecUnsupportdComAction,
        tBgpFlowRouteInvalid,
        tBgpMaxNgPrefixThreshReached
    }
    STATUS      obsolete
    DESCRIPTION
        "The group of notifications supporting management of extended BGP on
         Nokia SROS series systems release 11.0."
    ::= { tmnxBgpGroups 71 }

tmnxBgpObsoleteNtfnV11v0Group    NOTIFICATION-GROUP
    NOTIFICATIONS {
        tBgp4OptTransPathAttrInvalid,
        tBgp4OptTransWithdrawnRoutes
    }
    STATUS      current
    DESCRIPTION
        "The group of notifications supporting management of extended BGP on
         Nokia SROS series systems."
    ::= { tmnxBgpGroups 72 }

tmnxBgpMvpnVrfImportGroup        OBJECT-GROUP
    OBJECTS     {
        tBgpInstMvpnVrfImportSubTypeNew
    }
    STATUS      current
    DESCRIPTION
        "The group of objects supporting management of extended BGP on Nokia
         SROS series systems release 11.0."
    ::= { tmnxBgpGroups 73 }

tmnxBgpNHUnchangedGroup          OBJECT-GROUP
    OBJECTS     {
        tBgpPGNHUnchangedFamily,
        tBgpPeerNgNhUnchangedFamily
    }
    STATUS      current
    DESCRIPTION
        "The group of objects supporting management of next-hop unchanged
         family on Nokia SROS series systems release 11.0."
    ::= { tmnxBgpGroups 74 }

tmnxBgpResolveLabelRoutesGroup   OBJECT-GROUP
    OBJECTS     {
        tBgpInstResolveLabelRoutesInRtm
    }
    STATUS      current
    DESCRIPTION
        "The group of objects supporting BGP route reflector use of route table
         for labeled routes on Nokia SROS series systems release 12.0."
    ::= { tmnxBgpGroups 75 }

tmnxBgpInstanceV12v0Group        OBJECT-GROUP
    OBJECTS     {
        tBgpInstanceTableLastChanged,
        tBgpInstanceRowStatus,
        tBgpInstanceShutdown,
        tBgpInstanceDescription,
        tBgpInstanceAlwaysCompareMED,
        tBgpInstanceBgpId,
        tBgpInstanceConnectRetry,
        tBgpInstanceHoldTime,
        tBgpInstanceKeepAlive,
        tBgpInstanceDampening,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceIgpShortcut,
        tBgpInstanceDisallowIgp,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn,
        tBgpInstanceLocalAS4Byte,
        tBgpInstanceConfederationAS4Byte,
        tBgpInstanceDisable4ByteASN,
        tBgpInstanceMultipathEiBgpState,
        tBgpInstanceRemovePrivateASLmtd,
        tBgpInstancePlcyImportPolicy1,
        tBgpInstancePlcyImportPolicy2,
        tBgpInstancePlcyImportPolicy3,
        tBgpInstancePlcyImportPolicy4,
        tBgpInstancePlcyImportPolicy5,
        tBgpInstancePlcyImportPolicy6,
        tBgpInstancePlcyImportPolicy7,
        tBgpInstancePlcyImportPolicy8,
        tBgpInstancePlcyImportPolicy9,
        tBgpInstancePlcyImportPolicy10,
        tBgpInstancePlcyImportPolicy11,
        tBgpInstancePlcyImportPolicy12,
        tBgpInstancePlcyImportPolicy13,
        tBgpInstancePlcyImportPolicy14,
        tBgpInstancePlcyImportPolicy15,
        tBgpInstancePlcyExportPolicy1,
        tBgpInstancePlcyExportPolicy2,
        tBgpInstancePlcyExportPolicy3,
        tBgpInstancePlcyExportPolicy4,
        tBgpInstancePlcyExportPolicy5,
        tBgpInstancePlcyExportPolicy6,
        tBgpInstancePlcyExportPolicy7,
        tBgpInstancePlcyExportPolicy8,
        tBgpInstancePlcyExportPolicy9,
        tBgpInstancePlcyExportPolicy10,
        tBgpInstancePlcyExportPolicy11,
        tBgpInstancePlcyExportPolicy12,
        tBgpInstancePlcyExportPolicy13,
        tBgpInstancePlcyExportPolicy14,
        tBgpInstancePlcyExportPolicy15
    }
    STATUS      obsolete
    DESCRIPTION
        "The group of objects supporting management of each extended BGP
         instance on Nokia SROS series systems since release 12.0."
    ::= { tmnxBgpGroups 76 }

tmnxBgpPeerGroupV12v0Group       OBJECT-GROUP
    OBJECTS     {
        tBgpPeerGroupTableLastChanged,
        tBgpPeerGroupTableSpinlock,
        tBgpPeerGroupName,
        tBgpPeerGroupRowStatus,
        tBgpPeerGroupShutdown,
        tBgpPeerGroupDescription,
        tBgpPeerGroupConnectRetry,
        tBgpPeerGroupHoldTime,
        tBgpPeerGroupKeepAlive,
        tBgpPeerGroupDampening,
        tBgpPeerGroupLocalPreference,
        tBgpPeerGroupLoopDetect,
        tBgpPeerGroupMinRouteAdvertisement,
        tBgpPeerGroupMaxPrefix,
        tBgpPeerGroupMEDSource,
        tBgpPeerGroupMEDValue,
        tBgpPeerGroupMultihop,
        tBgpPeerGroupNextHopSelf,
        tBgpPeerGroupNoAggregatorID,
        tBgpPeerGroupPassive,
        tBgpPeerGroupPeerType,
        tBgpPeerGroupPreference,
        tBgpPeerGroupRemovePrivateAS,
        tBgpPeerGroupLastChanged,
        tBgpPeerGroupInheritance,
        tBgpPeerGroupOperStatus,
        tBgpPeerGroupLocalASPrivate,
        tBgpPeerGroupMd5Auth,
        tBgpPeerGroupMd5AuthKey,
        tBgpPeerGroupClusterId,
        tBgpPeerGroupDisableClientReflect,
        tBgpPeerGroupGracefulRestart,
        tBgpPeerGroupGRRestartTime,
        tBgpPeerGroupGRStaleRoute,
        tBgpPeerGroupGRAdminState,
        tBgpPeerGroupGROperState,
        tBgpPeerGroupFamily,
        tBgpPeerGroupVpnApplyImport,
        tBgpPeerGroupVpnApplyExport,
        tBgpPeerGroupASOverride,
        tBgpPeerGroupOrf,
        tBgpPeerGroupExtCommsOrf,
        tBgpPeerGroupExtCommsSendOrf,
        tBgpPeerGroupExtCommsRecvOrf,
        tBgpPGSendOrfRTRowStatus,
        tBgpPeerGroupLocalAS4Byte,
        tBgpPeerGroupPeerAS4Byte,
        tBgpPeerGroupDisable4ByteASN,
        tBgpPeerGroupRemovePrivateASLmtd,
        tBgpPeerGroupPlcyImportPolicy1,
        tBgpPeerGroupPlcyImportPolicy2,
        tBgpPeerGroupPlcyImportPolicy3,
        tBgpPeerGroupPlcyImportPolicy4,
        tBgpPeerGroupPlcyImportPolicy5,
        tBgpPeerGroupPlcyImportPolicy6,
        tBgpPeerGroupPlcyImportPolicy7,
        tBgpPeerGroupPlcyImportPolicy8,
        tBgpPeerGroupPlcyImportPolicy9,
        tBgpPeerGroupPlcyImportPolicy10,
        tBgpPeerGroupPlcyImportPolicy11,
        tBgpPeerGroupPlcyImportPolicy12,
        tBgpPeerGroupPlcyImportPolicy13,
        tBgpPeerGroupPlcyImportPolicy14,
        tBgpPeerGroupPlcyImportPolicy15,
        tBgpPeerGroupPlcyExportPolicy1,
        tBgpPeerGroupPlcyExportPolicy2,
        tBgpPeerGroupPlcyExportPolicy3,
        tBgpPeerGroupPlcyExportPolicy4,
        tBgpPeerGroupPlcyExportPolicy5,
        tBgpPeerGroupPlcyExportPolicy6,
        tBgpPeerGroupPlcyExportPolicy7,
        tBgpPeerGroupPlcyExportPolicy8,
        tBgpPeerGroupPlcyExportPolicy9,
        tBgpPeerGroupPlcyExportPolicy10,
        tBgpPeerGroupPlcyExportPolicy11,
        tBgpPeerGroupPlcyExportPolicy12,
        tBgpPeerGroupPlcyExportPolicy13,
        tBgpPeerGroupPlcyExportPolicy14,
        tBgpPeerGroupPlcyExportPolicy15
    }
    STATUS      obsolete
    DESCRIPTION
        "The group of objects supporting management of extended BGP Peer Groups
         on Nokia SROS series systems since release 12.0."
    ::= { tmnxBgpGroups 77 }

tmnxBgpPeerV12v0Group            OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgDampening,
        tBgpPeerNgLocalAddress,
        tBgpPeerNgLocalAddressType,
        tBgpPeerNgLocalPreference,
        tBgpPeerNgLoopDetect,
        tBgpPeerNgMinRouteAdvertisement,
        tBgpPeerNgMaxPrefix,
        tBgpPeerNgMEDSource,
        tBgpPeerNgMEDValue,
        tBgpPeerNgMultihop,
        tBgpPeerNgNextHopSelf,
        tBgpPeerNgNoAggregatorID,
        tBgpPeerNgPassive,
        tBgpPeerNgPeerType,
        tBgpPeerNgPreference,
        tBgpPeerNgRemovePrivateAS,
        tBgpPeerNgLastChanged,
        tBgpPeerNgInheritance,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs,
        tBgpPeerNgOperVpnIpv6RecvPfxs,
        tBgpPeerNgOperVpnIpv6SentPfxs,
        tBgpPeerNgOperVpnIpv6ActivePfxs,
        tBgpPeerNgOperVpnIpv6SuppPfxDamp,
        tBgpPeerNgLocalAS4Byte,
        tBgpPeerNgPeerAS4Byte,
        tBgpPeerNgDisable4ByteASN,
        tBgpPeerNgOperMvpnV4SuppPfxDamp,
        tBgpPeerNgOperMvpnV4RecvPfxs,
        tBgpPeerNgOperMvpnV4SentPfxs,
        tBgpPeerNgOperMvpnV4ActivePfxs,
        tBgpPeerNgL2vpnCiscoInterop,
        tBgpPeerNgRemovePrivateASLmtd,
        tBgpPeerPlcyImportPolicy1,
        tBgpPeerPlcyImportPolicy2,
        tBgpPeerPlcyImportPolicy3,
        tBgpPeerPlcyImportPolicy4,
        tBgpPeerPlcyImportPolicy5,
        tBgpPeerPlcyImportPolicy6,
        tBgpPeerPlcyImportPolicy7,
        tBgpPeerPlcyImportPolicy8,
        tBgpPeerPlcyImportPolicy9,
        tBgpPeerPlcyImportPolicy10,
        tBgpPeerPlcyImportPolicy11,
        tBgpPeerPlcyImportPolicy12,
        tBgpPeerPlcyImportPolicy13,
        tBgpPeerPlcyImportPolicy14,
        tBgpPeerPlcyImportPolicy15,
        tBgpPeerPlcyExportPolicy1,
        tBgpPeerPlcyExportPolicy2,
        tBgpPeerPlcyExportPolicy3,
        tBgpPeerPlcyExportPolicy4,
        tBgpPeerPlcyExportPolicy5,
        tBgpPeerPlcyExportPolicy6,
        tBgpPeerPlcyExportPolicy7,
        tBgpPeerPlcyExportPolicy8,
        tBgpPeerPlcyExportPolicy9,
        tBgpPeerPlcyExportPolicy10,
        tBgpPeerPlcyExportPolicy11,
        tBgpPeerPlcyExportPolicy12,
        tBgpPeerPlcyExportPolicy13,
        tBgpPeerPlcyExportPolicy14,
        tBgpPeerPlcyExportPolicy15
    }
    STATUS      obsolete
    DESCRIPTION
        "The group of objects supporting management of extended BGP peers on
         Nokia SROS series systems since release 12.0."
    ::= { tmnxBgpGroups 78 }

tmnxBgpObsoleteV12v0Group        OBJECT-GROUP
    OBJECTS     {
        tBgpInstanceMinASOrigination,
        tBgpPeerGroupMinASOrigination,
        tBgpPeerNgMinASOrigination
    }
    STATUS      current
    DESCRIPTION
        "The group of objects in TIMETRA-BGP-MIB which are obsoleted in Nokia
         SROS 12.0 series systems."
    ::= { tmnxBgpGroups 79 }

tmnxBgpMcastIpv6Group            OBJECT-GROUP
    OBJECTS     {
        tBgpPeerNgOperMcastV6SupPfxDamp,
        tBgpPeerNgOperMcastV6RecvPfxs,
        tBgpPeerNgOperMcastV6SentPfxs,
        tBgpPeerNgOperMcastV6ActivePfxs
    }
    STATUS      current
    DESCRIPTION
        "The group of objects supporting BGP address family of mcast-ipv6
         routes on Nokia SROS series systems release 11.0."
    ::= { tmnxBgpGroups 80 }

tmnxBgpPrefixOriginValidGroup    OBJECT-GROUP
    OBJECTS     {
        tBgpInstanceCompOriginValidState,
        tBgpPGEnableOriginValidation,
        tBgpPeerNgEnableOriginValidation,
        tBgpInstanceOrigInvalidUnusable
    }
    STATUS      current
    DESCRIPTION
        "The group of objects supporting BGP Peer Origin Validation on Nokia
         SROS series systems release 12.0."
    ::= { tmnxBgpGroups 81 }

tmnxBgpThirdPartyNHGroup         OBJECT-GROUP
    OBJECTS     {
        tBgpInstanceThirdPartyNextHop,
        tBgpPGThirdPartyNextHop,
        tBgpPeerNgThirdPartyNextHop
    }
    STATUS      current
    DESCRIPTION
        "The group of objects supporting BGP third party next-hop processing on
         Nokia SROS series systems since release 12.0."
    ::= { tmnxBgpGroups 82 }

tmnxBgpNotificationV12v0Group    NOTIFICATION-GROUP
    NOTIFICATIONS {
        tBgpReceivedInvalidNlri
    }
    STATUS      current
    DESCRIPTION
        "The group of notifications supporting management of extended BGP on
         Nokia SROS series systems release 12.0."
    ::= { tmnxBgpGroups 83 }

tmnxBgpNotifyObjsV12v0Group      OBJECT-GROUP
    OBJECTS     {
        tBgp4BadErrorMessage,
        tBgp4BadErrorMessageType
    }
    STATUS      current
    DESCRIPTION
        "The group of notify objects supporting management of extended BGP on
         Nokia SROS series systems release 12.0."
    ::= { tmnxBgpGroups 84 }

tmnxBgpPeerGroupV13v0Group       OBJECT-GROUP
    OBJECTS     {
        tBgpPeerGroupPfxLmtTableLstChgd,
        tBgpPeerGroupPfxLmtLastChanged,
        tBgpPeerGroupPfxLmtRowStatus,
        tBgpPeerGroupPfxLmtMaxPrefix,
        tBgpPeerGroupPfxLmtLogOnly,
        tBgpPeerGroupPfxLmtThreshold,
        tBgpPeerGroupPfxLmtIdleTimeOut,
        tBgpPeerGroupPfxLmtPostImport,
        tBgpPeerNgPfxLmtTableLstChgd,
        tBgpPeerNgPfxLmtLastChanged,
        tBgpPeerNgPfxLmtRowStatus,
        tBgpPeerNgPfxLmtMaxPrefix,
        tBgpPeerNgPfxLmtLogOnly,
        tBgpPeerNgPfxLmtThreshold,
        tBgpPeerNgPfxLmtIdleTimeOut,
        tBgpPeerNgPfxLmtPostImport,
        tBgpPeerNgPfxLmtInheritance
    }
    STATUS      current
    DESCRIPTION
        "The group of objects supporting management of extended BGP Peer Groups
         and peers on Nokia SROS series systems since release 13.0."
    ::= { tmnxBgpGroups 85 }

tmnxBgpNotificationV13v0Group    NOTIFICATION-GROUP
    NOTIFICATIONS {
        tBgpMaxNgPfxLmt,
        tBgpMaxNgPfxLmtThresholdReached
    }
    STATUS      current
    DESCRIPTION
        "The group of notifications supporting management of extended BGP on
         Nokia SROS series systems release 13.0."
    ::= { tmnxBgpGroups 86 }

tmnxBgpLinkBandwidthExtCommGroup OBJECT-GROUP
    OBJECTS     {
        tBgpPGAddLinkBandwidth,
        tBgpPeerNgAddLinkBandwidth
    }
    STATUS      current
    DESCRIPTION
        "The group of objects supporting BGP Link Bandwidth Extended Community
         on Nokia SROS series systems since release 13.0."
    ::= { tmnxBgpGroups 87 }

tmnxBgpRibLeakImportV13v0Group   OBJECT-GROUP
    OBJECTS     {
        tBgpRibLeakImportPolicyTblLstCh,
        tBgpRibLeakImportPolicyLstCh,
        tBgpRibLeakImportPolicy1,
        tBgpRibLeakImportPolicy2,
        tBgpRibLeakImportPolicy3,
        tBgpRibLeakImportPolicy4,
        tBgpRibLeakImportPolicy5,
        tBgpRibLeakImportPolicy6,
        tBgpRibLeakImportPolicy7,
        tBgpRibLeakImportPolicy8,
        tBgpRibLeakImportPolicy9,
        tBgpRibLeakImportPolicy10,
        tBgpRibLeakImportPolicy11,
        tBgpRibLeakImportPolicy12,
        tBgpRibLeakImportPolicy13,
        tBgpRibLeakImportPolicy14,
        tBgpRibLeakImportPolicy15
    }
    STATUS      current
    DESCRIPTION
        "The group of objects supporting management of BGP RIB leak import
         policies on Nokia SROS series systems since release 13.0."
    ::= { tmnxBgpGroups 88 }

tmnxBgpShortcutTunnelV13v0Group  OBJECT-GROUP
    OBJECTS     {
        tBgpShortcutTunnelTblLstCh,
        tBgpShortcutTunnelLstCh,
        tBgpShortcutTunnelResolution,
        tBgpShortcutTunnelLdp,
        tBgpShortcutTunnelRsvpTe,
        tBgpShortcutTunnelBgp,
        tBgpShortcutTunnelDisallowIgp,
        tBgpShortcutTunnelSrIsis,
        tBgpShortcutTunnelSrOspf
    }
    STATUS      current
    DESCRIPTION
        "The group of objects supporting management of BGP shortcut using
         segmented routing tunnel on Nokia SROS series systems since release
         13.0."
    ::= { tmnxBgpGroups 89 }

tmnxBgpLabelRtTunnelV13v0Group   OBJECT-GROUP
    OBJECTS     {
        tBgpLabelRtTunnelTblLstCh,
        tBgpLabelRtTunnelLstCh,
        tBgpLabelRtTunnelResolution,
        tBgpLabelRtTunnelLdp,
        tBgpLabelRtTunnelRsvpTe,
        tBgpLabelRtTunnelSrIsis,
        tBgpLabelRtTunnelSrOspf
    }
    STATUS      current
    DESCRIPTION
        "The group of objects supporting management of BGP labelled route
         resolution using segmented routing tunnel on Nokia SROS series systems
         since release 13.0."
    ::= { tmnxBgpGroups 90 }

tmnxBgpDynamicPeerLmtV13v0Group  OBJECT-GROUP
    OBJECTS     {
        tBgpInstanceDynamicPeerLimit,
        tBgpPGDynamicPeerLimit,
        tBgpPGDynamicPeerPfxTableLstChgd,
        tBgpPGDynamicPeerPfxLastChanged,
        tBgpPGDynamicPeerPfxRowStatus,
        tBgpPGDynamicPeerPfxGroupName
    }
    STATUS      current
    DESCRIPTION
        "The group of objects supporting management of BGP Dynamic Peer on
         Nokia SROS series systems since release 13.0."
    ::= { tmnxBgpGroups 91 }

tmnxBgpPeerGroupV13v1Group       OBJECT-GROUP
    OBJECTS     {
        tBgpPeerGroupTableLastChanged,
        tBgpPeerGroupTableSpinlock,
        tBgpPeerGroupName,
        tBgpPeerGroupRowStatus,
        tBgpPeerGroupShutdown,
        tBgpPeerGroupDescription,
        tBgpPeerGroupConnectRetry,
        tBgpPeerGroupHoldTime,
        tBgpPeerGroupKeepAlive,
        tBgpPeerGroupDampening,
        tBgpPeerGroupLocalPreference,
        tBgpPeerGroupLoopDetect,
        tBgpPeerGroupMinRouteAdvertisement,
        tBgpPeerGroupMEDSource,
        tBgpPeerGroupMEDValue,
        tBgpPeerGroupMultihop,
        tBgpPeerGroupNextHopSelf,
        tBgpPeerGroupNoAggregatorID,
        tBgpPeerGroupPassive,
        tBgpPeerGroupPeerType,
        tBgpPeerGroupPreference,
        tBgpPeerGroupRemovePrivateAS,
        tBgpPeerGroupLastChanged,
        tBgpPeerGroupInheritance,
        tBgpPeerGroupOperStatus,
        tBgpPeerGroupLocalASPrivate,
        tBgpPeerGroupMd5Auth,
        tBgpPeerGroupMd5AuthKey,
        tBgpPeerGroupClusterId,
        tBgpPeerGroupDisableClientReflect,
        tBgpPeerGroupGracefulRestart,
        tBgpPeerGroupGRRestartTime,
        tBgpPeerGroupGRStaleRoute,
        tBgpPeerGroupGRAdminState,
        tBgpPeerGroupGROperState,
        tBgpPeerGroupFamily,
        tBgpPeerGroupVpnApplyImport,
        tBgpPeerGroupVpnApplyExport,
        tBgpPeerGroupASOverride,
        tBgpPeerGroupOrf,
        tBgpPeerGroupExtCommsOrf,
        tBgpPeerGroupExtCommsSendOrf,
        tBgpPeerGroupExtCommsRecvOrf,
        tBgpPGSendOrfRTRowStatus,
        tBgpPeerGroupLocalAS4Byte,
        tBgpPeerGroupPeerAS4Byte,
        tBgpPeerGroupDisable4ByteASN,
        tBgpPeerGroupRemovePrivateASLmtd,
        tBgpPeerGroupPlcyImportPolicy1,
        tBgpPeerGroupPlcyImportPolicy2,
        tBgpPeerGroupPlcyImportPolicy3,
        tBgpPeerGroupPlcyImportPolicy4,
        tBgpPeerGroupPlcyImportPolicy5,
        tBgpPeerGroupPlcyImportPolicy6,
        tBgpPeerGroupPlcyImportPolicy7,
        tBgpPeerGroupPlcyImportPolicy8,
        tBgpPeerGroupPlcyImportPolicy9,
        tBgpPeerGroupPlcyImportPolicy10,
        tBgpPeerGroupPlcyImportPolicy11,
        tBgpPeerGroupPlcyImportPolicy12,
        tBgpPeerGroupPlcyImportPolicy13,
        tBgpPeerGroupPlcyImportPolicy14,
        tBgpPeerGroupPlcyImportPolicy15,
        tBgpPeerGroupPlcyExportPolicy1,
        tBgpPeerGroupPlcyExportPolicy2,
        tBgpPeerGroupPlcyExportPolicy3,
        tBgpPeerGroupPlcyExportPolicy4,
        tBgpPeerGroupPlcyExportPolicy5,
        tBgpPeerGroupPlcyExportPolicy6,
        tBgpPeerGroupPlcyExportPolicy7,
        tBgpPeerGroupPlcyExportPolicy8,
        tBgpPeerGroupPlcyExportPolicy9,
        tBgpPeerGroupPlcyExportPolicy10,
        tBgpPeerGroupPlcyExportPolicy11,
        tBgpPeerGroupPlcyExportPolicy12,
        tBgpPeerGroupPlcyExportPolicy13,
        tBgpPeerGroupPlcyExportPolicy14,
        tBgpPeerGroupPlcyExportPolicy15
    }
    STATUS      current
    DESCRIPTION
        "The group of objects supporting management of extended BGP Peer Groups
         on Nokia SROS series systems since release 13.0."
    ::= { tmnxBgpGroups 92 }

tmnxBgpGlobalV13v0Group          OBJECT-GROUP
    OBJECTS     {
        tBgpInstancePMTUDiscovery,
        tBgpPeerGroupPMTUDiscovery,
        tBgpPeerNgPMTUDiscovery,
        tBgpPeerNgAdvertiseLdpPrefix,
        tBgpPrngPlcyMaxPrefixLogOnly,
        tBgpPrngPlcyMaxPrefixThreshold
    }
    STATUS      current
    DESCRIPTION
        "The group of objects supporting management of extended BGP on Nokia
         SROS series systems release 13.0."
    ::= { tmnxBgpGroups 93 }

tmnxBgpGlobalV13v1Group          OBJECT-GROUP
    OBJECTS     {
        tBgpInstLocalASNoPrependGlobalAS,
        tBgpPGLocalASNoPrependGlobalAS,
        tBgpPeerNgLclASNoPrependGlobalAS,
        tBgpPeerNgOperMvpnV6SuppPfxDamp,
        tBgpPeerNgOperMvpnV6RecvPfxs,
        tBgpPeerNgOperMvpnV6SentPfxs,
        tBgpPeerNgOperMvpnV6ActivePfxs,
        tBgpInstanceEnableRRVpnFwding,
        tBgpPeerNgOperFlowIpv6SupPfxDamp,
        tBgpPeerNgOperFlowIpv6RecvPfxs,
        tBgpPeerNgOperFlowIpv6SentPfxs,
        tBgpPeerNgOperFlowIpv6ActivePfxs,
        tBgpInstanceNHResPolicy,
        tBgpInstancePeerTrackingPolicy,
        tBgpInstanceAdvertiseExternal,
        tBgpInstanceBackupPath,
        tBgpInstanceDisableRtTblInstall,
        tBgpInstanceDeterministicMED,
        tBgpInstanceSplitHorizon,
        tBgpPGSplitHorizon,
        tBgpInstanceIgnoreRtrIdInternal,
        tBgpInstanceIgnoreRtrIdExternal
    }
    STATUS      current
    DESCRIPTION
        "The group of objects supporting management of extended BGP on Nokia
         SROS series systems release 13.0."
    ::= { tmnxBgpGroups 94 }

tmnxBgpPeerV13v0Group            OBJECT-GROUP
    OBJECTS     {
        tBgpPeerTableLastChanged,
        tBgpPeerTableSpinlock,
        tBgpPeerNgPeerGroup,
        tBgpPeerNgRowStatus,
        tBgpPeerNgShutdown,
        tBgpPeerNgDescription,
        tBgpPeerNgConnectRetry,
        tBgpPeerNgHoldTime,
        tBgpPeerNgKeepAlive,
        tBgpPeerNgDampening,
        tBgpPeerNgLocalAddress,
        tBgpPeerNgLocalAddressType,
        tBgpPeerNgLocalPreference,
        tBgpPeerNgLoopDetect,
        tBgpPeerNgMinRouteAdvertisement,
        tBgpPeerNgMEDSource,
        tBgpPeerNgMEDValue,
        tBgpPeerNgMultihop,
        tBgpPeerNgNextHopSelf,
        tBgpPeerNgNoAggregatorID,
        tBgpPeerNgPassive,
        tBgpPeerNgPeerType,
        tBgpPeerNgPreference,
        tBgpPeerNgRemovePrivateAS,
        tBgpPeerNgLastChanged,
        tBgpPeerNgInheritance,
        tBgpPeerNgExportPolicy1,
        tBgpPeerNgExportPolicy2,
        tBgpPeerNgExportPolicy3,
        tBgpPeerNgExportPolicy4,
        tBgpPeerNgExportPolicy5,
        tBgpPeerNgOperStatus,
        tBgpPeerNgLocalASPrivate,
        tBgpPeerNgMd5Auth,
        tBgpPeerNgMd5AuthKey,
        tBgpPeerNgClusterId,
        tBgpPeerNgDisableClientReflect,
        tBgpPeerNgGracefulRestart,
        tBgpPeerNgGRRestartTime,
        tBgpPeerNgGRStaleRoute,
        tBgpPeerNgGRAdminState,
        tBgpPeerNgGROperState,
        tBgpPeerNgFamily,
        tBgpPeerNgVpnRemoteFamily,
        tBgpPeerNgVpnApplyImport,
        tBgpPeerNgVpnApplyExport,
        tBgpPeerNgVpnLocalCaps,
        tBgpPeerNgVpnRemoteCaps,
        tBgpPeerNgConnState,
        tBgpPeerNgASOverride,
        tBgpPeerNgOrf,
        tBgpPeerNgExtCommsOrf,
        tBgpPeerNgExtCommsSendOrf,
        tBgpPeerNgExtCommsRecvOrf,
        tBgpPeerNgOperMsgOctetsRcvd,
        tBgpPeerNgOperMsgOctetsSent,
        tBgpPeerNgOperInputQueueMsgs,
        tBgpPeerNgOperOutputQueueMsgs,
        tBgpPeerNgOperReceivedPrefixes,
        tBgpPeerNgOperSentPrefixes,
        tBgpPeerNgOperActivePrefixes,
        tBgpPeerNgOperReceivedPaths,
        tBgpPeerNgOperFlaps,
        tBgpPeerNgOperLastState,
        tBgpPeerNgOperLastEvent,
        tBgpPeerNgOperVpnRecvPrefixes,
        tBgpPeerNgOperVpnSentPrefixes,
        tBgpPeerNgOperVpnActivePrefixes,
        tBgpPeerNgSendOrfRTRowStatus,
        tBgpPeerNgOperGRSupport,
        tBgpPeerNgOperGRFamilyRestart,
        tBgpPeerNgOperGRFamilyFwding,
        tBgpPeerNgOperGRFamilyNegotiated,
        tBgpPeerNgOperGRRecvEOR,
        tBgpPeerNgOperGRSendEOR,
        tBgpPeerNgOperGRStaleRoutesTime,
        tBgpPeerNgOperGRReqRestartTime,
        tBgpPeerNgOperGRStatus,
        tBgpPeerNgOperNumRestarts,
        tBgpPeerNgOperLastRestartTime,
        tBgpPeerNgOperV6ReceivedPrefixes,
        tBgpPeerNgOperV6SentPrefixes,
        tBgpPeerNgOperV6ActivePrefixes,
        tBgpPeerNgOperV4SuppPfxDamp,
        tBgpPeerNgOperVpnSuppPfxDamp,
        tBgpPeerNgOperV6SuppPfxDamp,
        tBgpPeerNgOperMCastV4SuppPfxDamp,
        tBgpPeerNgOperMCastV4RecvPfxs,
        tBgpPeerNgOperMCastV4SentPfxs,
        tBgpPeerNgOperMCastV4ActivePfxs,
        tBgpPeerNgOperVpnIpv6RecvPfxs,
        tBgpPeerNgOperVpnIpv6SentPfxs,
        tBgpPeerNgOperVpnIpv6ActivePfxs,
        tBgpPeerNgOperVpnIpv6SuppPfxDamp,
        tBgpPeerNgLocalAS4Byte,
        tBgpPeerNgPeerAS4Byte,
        tBgpPeerNgDisable4ByteASN,
        tBgpPeerNgOperMvpnV4SuppPfxDamp,
        tBgpPeerNgOperMvpnV4RecvPfxs,
        tBgpPeerNgOperMvpnV4SentPfxs,
        tBgpPeerNgOperMvpnV4ActivePfxs,
        tBgpPeerNgL2vpnCiscoInterop,
        tBgpPeerNgRemovePrivateASLmtd,
        tBgpPeerPlcyImportPolicy1,
        tBgpPeerPlcyImportPolicy2,
        tBgpPeerPlcyImportPolicy3,
        tBgpPeerPlcyImportPolicy4,
        tBgpPeerPlcyImportPolicy5,
        tBgpPeerPlcyImportPolicy6,
        tBgpPeerPlcyImportPolicy7,
        tBgpPeerPlcyImportPolicy8,
        tBgpPeerPlcyImportPolicy9,
        tBgpPeerPlcyImportPolicy10,
        tBgpPeerPlcyImportPolicy11,
        tBgpPeerPlcyImportPolicy12,
        tBgpPeerPlcyImportPolicy13,
        tBgpPeerPlcyImportPolicy14,
        tBgpPeerPlcyImportPolicy15,
        tBgpPeerPlcyExportPolicy1,
        tBgpPeerPlcyExportPolicy2,
        tBgpPeerPlcyExportPolicy3,
        tBgpPeerPlcyExportPolicy4,
        tBgpPeerPlcyExportPolicy5,
        tBgpPeerPlcyExportPolicy6,
        tBgpPeerPlcyExportPolicy7,
        tBgpPeerPlcyExportPolicy8,
        tBgpPeerPlcyExportPolicy9,
        tBgpPeerPlcyExportPolicy10,
        tBgpPeerPlcyExportPolicy11,
        tBgpPeerPlcyExportPolicy12,
        tBgpPeerPlcyExportPolicy13,
        tBgpPeerPlcyExportPolicy14,
        tBgpPeerPlcyExportPolicy15
    }
    STATUS      current
    DESCRIPTION
        "The group of objects supporting management of extended BGP peers on
         Nokia SROS series systems since release 13.0."
    ::= { tmnxBgpGroups 95 }

tmnxBgpObsoleteV13v0Group        OBJECT-GROUP
    OBJECTS     {
        tBgpPeerGroupMaxPrefix,
        tBgpPeerGroupMaxPrefixLogOnly,
        tBgpPeerGroupMaxPrefixThreshold,
        tBgpPGMaxPrefixIdleTimeOut,
        tBgpPeerNgMaxPrefix,
        tBgpPeerNgMaxPrefixLogOnly,
        tBgpPeerNgMaxPrefixThreshold,
        tBgpPeerNgMaxPrefixIdleTimeOut,
        tBgpInstanceTransportTunnel,
        tBgpInstanceIgpShortcut,
        tBgpInstanceDisallowIgp
    }
    STATUS      current
    DESCRIPTION
        "The group of objects in TIMETRA-BGP-MIB which are obsoleted in Nokia
         SROS 13.0 series systems."
    ::= { tmnxBgpGroups 96 }

tmnxBgpNotificationV13v1Group    NOTIFICATION-GROUP
    NOTIFICATIONS {
        tBgp4UpdateInvalid,
        tBgp4PathAttrInvalid,
        tBgp4WithdrawnRtFromUpdateError,
        tBgpPeerNgGRStatusChange,
        tBgpNgEstablished,
        tBgpNgBackwardTransition,
        tBgpFlowspecUnsupportdComAction
    }
    STATUS      current
    DESCRIPTION
        "The group of notifications supporting management of extended BGP on
         Nokia SROS series systems release 13.0."
    ::= { tmnxBgpGroups 97 }

tmnxBgpObsoletedNtfnV13v0Group   NOTIFICATION-GROUP
    NOTIFICATIONS {
        tBgpMaxNgPrefix100,
        tBgpMaxNgPrefixThreshReached
    }
    STATUS      current
    DESCRIPTION
        "The group of notifications which are obsoleted in Nokia SROS series
         systems release 13.0."
    ::= { tmnxBgpGroups 98 }

tmnxBgpInstanceV13v0Group        OBJECT-GROUP
    OBJECTS     {
        tBgpInstanceTableLastChanged,
        tBgpInstanceRowStatus,
        tBgpInstanceShutdown,
        tBgpInstanceDescription,
        tBgpInstanceAlwaysCompareMED,
        tBgpInstanceBgpId,
        tBgpInstanceConnectRetry,
        tBgpInstanceHoldTime,
        tBgpInstanceKeepAlive,
        tBgpInstanceDampening,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn,
        tBgpInstanceLocalAS4Byte,
        tBgpInstanceConfederationAS4Byte,
        tBgpInstanceDisable4ByteASN,
        tBgpInstanceMultipathEiBgpState,
        tBgpInstanceRemovePrivateASLmtd,
        tBgpInstancePlcyImportPolicy1,
        tBgpInstancePlcyImportPolicy2,
        tBgpInstancePlcyImportPolicy3,
        tBgpInstancePlcyImportPolicy4,
        tBgpInstancePlcyImportPolicy5,
        tBgpInstancePlcyImportPolicy6,
        tBgpInstancePlcyImportPolicy7,
        tBgpInstancePlcyImportPolicy8,
        tBgpInstancePlcyImportPolicy9,
        tBgpInstancePlcyImportPolicy10,
        tBgpInstancePlcyImportPolicy11,
        tBgpInstancePlcyImportPolicy12,
        tBgpInstancePlcyImportPolicy13,
        tBgpInstancePlcyImportPolicy14,
        tBgpInstancePlcyImportPolicy15,
        tBgpInstancePlcyExportPolicy1,
        tBgpInstancePlcyExportPolicy2,
        tBgpInstancePlcyExportPolicy3,
        tBgpInstancePlcyExportPolicy4,
        tBgpInstancePlcyExportPolicy5,
        tBgpInstancePlcyExportPolicy6,
        tBgpInstancePlcyExportPolicy7,
        tBgpInstancePlcyExportPolicy8,
        tBgpInstancePlcyExportPolicy9,
        tBgpInstancePlcyExportPolicy10,
        tBgpInstancePlcyExportPolicy11,
        tBgpInstancePlcyExportPolicy12,
        tBgpInstancePlcyExportPolicy13,
        tBgpInstancePlcyExportPolicy14,
        tBgpInstancePlcyExportPolicy15
    }
    STATUS      obsolete
    DESCRIPTION
        "The group of objects supporting management of each extended BGP
         instance on Nokia SROS series systems since release 13.0."
    ::= { tmnxBgpGroups 99 }

tmnxBgpPeerNgV13v0Group          OBJECT-GROUP
    OBJECTS     {
        tBgpPeerNgOperIpv4RejPfxs,
        tBgpPeerNgOperVpnIpv4RejPfxs,
        tBgpPeerNgOperIpv6RejPfxs,
        tBgpPeerNgOperVpnIpv6RejPfxs,
        tBgpPeerNgOperMCastV4RejPfxs,
        tBgpPeerNgOperl2VpnRejPfxs,
        tBgpPeerNgOperMvpnV4RejPfxs,
        tBgpPeerNgOperMdtSafiRejPfxs,
        tBgpPeerNgOperMsPwRejPfxs,
        tBgpPeerNgOperFlowIpv4RejPfxs,
        tBgpPeerNgOperRtTgtRejPfxs,
        tBgpPeerNgOperMcastVpnV4RejPfxs,
        tBgpPeerNgOperMvpnV6RejPfxs,
        tBgpPeerNgOperFlowIpv6RejPfxs,
        tBgpPeerNgOperEvpnRejPfxs,
        tBgpPeerNgOperMCastV6RejPfxs,
        tBgpPeerNgOperMcVpnV4SuppPfxDamp
    }
    STATUS      current
    DESCRIPTION
        "The group of objects supporting management of extended BGP peers on
         Nokia SROS series systems since release 13.0."
    ::= { tmnxBgpGroups 100 }

tmnxBgpPeerNgDynamicV13v0Group   OBJECT-GROUP
    OBJECTS     {
        tBgpPeerNgCreationType
    }
    STATUS      current
    DESCRIPTION
        "The group of objects supporting management of extended BGP peers on
         Nokia SROS series systems since release 13.0."
    ::= { tmnxBgpGroups 101 }

tmnxBgpPeerNgEvpnMplsV13v0Group  OBJECT-GROUP
    OBJECTS     {
        tBgpPeerNgDefRxEvpnEncap
    }
    STATUS      current
    DESCRIPTION
        "The group of objects supporting management of extended BGP peers on
         Nokia SROS series systems since release 13.0."
    ::= { tmnxBgpGroups 102 }

tmnxBgpDynPeerLmtNtfnV13v0Group  NOTIFICATION-GROUP
    NOTIFICATIONS {
        tBgpInstanceDynamicPeerLmtReachd,
        tBgpPGDynamicPeerLmtReached
    }
    STATUS      current
    DESCRIPTION
        "The group of notifications supporting management of extended BGP on
         Nokia SROS series systems release 13.0."
    ::= { tmnxBgpGroups 103 }

tmnxBgpMultiPathV14v0Group       OBJECT-GROUP
    OBJECTS     {
        tBgpInstanceMultipathBgp,
        tBgpInstanceMultipathEBgp,
        tBgpInstanceMultipathIBgp,
        tBgpInstanceMultipathRestrict,
        tBgpInstanceEbgpIbgpEqual
    }
    STATUS      current
    DESCRIPTION
        "The group of objects supporting management of each extended BGP
         instance on Nokia SROS series systems release 14.0."
    ::= { tmnxBgpGroups 104 }

tmnxBgpPeerNgV14v0Group          OBJECT-GROUP
    OBJECTS     {
        tBgpPGLabelResolveStatic,
        tBgpPeerNgLabelResolveStatic
    }
    STATUS      obsolete
    DESCRIPTION
        "The group of objects supporting management of each extended BGP peers
         on Nokia SROS series systems since release 14.0."
    ::= { tmnxBgpGroups 105 }

tmnxBgpLabelRtTunnelV14v0Group   OBJECT-GROUP
    OBJECTS     {
        tBgpLabelRtTunnelBgp,
        tBgpLabelRtTunnelSrTe
    }
    STATUS      current
    DESCRIPTION
        "The group of objects supporting management of BGP labelled route
         resolution using segmented routing tunnel on Nokia SROS series systems
         since release 14.0."
    ::= { tmnxBgpGroups 106 }

tmnxBgpShortcutTunnelV14v0Group  OBJECT-GROUP
    OBJECTS     {
        tBgpShortcutTunnelSrTe
    }
    STATUS      current
    DESCRIPTION
        "The group of objects supporting management of BGP shortcut using
         segmented routing tunnel on Nokia SROS series systems since release
         14.0."
    ::= { tmnxBgpGroups 107 }

tmnxBgpEntropyLabelV14v0Group    OBJECT-GROUP
    OBJECTS     {
        tBgpInstanceOverrideTunnelElc
    }
    STATUS      current
    DESCRIPTION
        "The group of objects supporting management of each extended BGP
         instance on Nokia SROS series systems release 14.0."
    ::= { tmnxBgpGroups 108 }

tmnxBgpRibRouteImportV14v0Group  OBJECT-GROUP
    OBJECTS     {
        tBgpRibControlTblLstCh,
        tBgpRibControlLstCh,
        tBgpRibImportFromRtmPolicy
    }
    STATUS      current
    DESCRIPTION
        "The group of objects supporting management of BGP routes in the RTM to
         be imported in RIB on Nokia SROS series systems release 14.0."
    ::= { tmnxBgpGroups 109 }

tmnxBgpLblRibSeparateV14v0Group  OBJECT-GROUP
    OBJECTS     {
        tBgpPeerNgLblIpv4AddPathLimit,
        tBgpPGLblIpv4AddPathLimit,
        tBgpInstanceLblIpv4AddPathLimit,
        tBgpPeerNgLblIpv6AddPathLimit,
        tBgpPGLblIpv6AddPathLimit,
        tBgpInstanceLblIpv6AddPathLimit,
        tBgpInstanceLabelPreference,
        tBgpPGLabelPreference,
        tBgpPeerNgLabelPreference
    }
    STATUS      obsolete
    DESCRIPTION
        "The group of objects supporting BGP ADD-PATH on Nokia SROS series
         systems release 14.0."
    ::= { tmnxBgpGroups 110 }

tmnxPeerNgV14v1Group             OBJECT-GROUP
    OBJECTS     {
        tBgpPeerNgOperLabelV4SupPfxDamp,
        tBgpPeerNgOperLabelV4RecvPfxs,
        tBgpPeerNgOperLabelV4SentPfxs,
        tBgpPeerNgOperLabelV4ActivePfxs,
        tBgpPeerNgOperLabelV4RejPfxs,
        tBgpPeerNgOperLabelV4BackupPfxs,
        tBgpPeerNgOperLabelV6SupPfxDamp,
        tBgpPeerNgOperLabelV6RecvPfxs,
        tBgpPeerNgOperLabelV6SentPfxs,
        tBgpPeerNgOperLabelV6ActivePfxs,
        tBgpPeerNgOperLabelV6RejPfxs,
        tBgpPeerNgOperLabelV6BackupPfxs,
        tBgpPeerNgOperBgpLsSupPfxDamp,
        tBgpPeerNgOperBgpLsRecvPfxs,
        tBgpPeerNgOperBgpLsSentPfxs,
        tBgpPeerNgOperBgpLsActivePfxs,
        tBgpPeerNgOperBgpLsRejPfxs
    }
    STATUS      current
    DESCRIPTION
        "The group of objects supporting management of extended BGP peers on
         Nokia SROS series systems since release 14.0."
    ::= { tmnxBgpGroups 111 }

tmnxBgpObsoleteV14v0Group        OBJECT-GROUP
    OBJECTS     {
        tBgpInstanceMultipath
    }
    STATUS      current
    DESCRIPTION
        "The group of objects in TIMETRA-BGP-MIB which are obsoleted in Nokia
         SROS 14.0 series systems."
    ::= { tmnxBgpGroups 112 }

tmnxBgpInstanceV14v0Group        OBJECT-GROUP
    OBJECTS     {
        tBgpInstanceTableLastChanged,
        tBgpInstanceRowStatus,
        tBgpInstanceShutdown,
        tBgpInstanceDescription,
        tBgpInstanceAlwaysCompareMED,
        tBgpInstanceBgpId,
        tBgpInstanceConnectRetry,
        tBgpInstanceHoldTime,
        tBgpInstanceKeepAlive,
        tBgpInstanceDampening,
        tBgpInstanceLocalPreference,
        tBgpInstanceLoopDetect,
        tBgpInstanceMinRouteAdvertisement,
        tBgpInstanceMultipath,
        tBgpInstanceNoAggregatorID,
        tBgpInstancePreference,
        tBgpInstanceRemovePrivateAS,
        tBgpInstanceLastChanged,
        tBgpInstanceMultihop,
        tBgpInstanceMEDSource,
        tBgpInstanceMEDValue,
        tBgpInstanceOperStatus,
        tBgpInstanceLocalASPrivate,
        tBgpInstanceMd5Auth,
        tBgpInstanceMd5AuthKey,
        tBgpInstanceClusterId,
        tBgpInstanceDisableClientReflect,
        tBgpInstanceIBgpMultipath,
        tBgpInstanceFamily,
        tBgpInstanceGracefulRestart,
        tBgpInstanceGRPathSelectDefer,
        tBgpInstanceGRRestartTime,
        tBgpInstanceGRStaleRoute,
        tBgpInstanceGRAdminState,
        tBgpInstanceGROperState,
        tBgpInstanceVpnApplyImport,
        tBgpInstanceVpnApplyExport,
        tBgpInstanceOrf,
        tBgpInstanceExtCommsOrf,
        tBgpInstanceExtCommsSendOrf,
        tBgpInstanceExtCommsRecvOrf,
        tBgpInstRteTargetRowStatus,
        tBgpSendOrfRTRowStatus,
        tBgpInstanceAllowInterAsVpn,
        tBgpInstanceLocalAS4Byte,
        tBgpInstanceConfederationAS4Byte,
        tBgpInstanceDisable4ByteASN,
        tBgpInstanceMultipathEiBgpState,
        tBgpInstanceRemovePrivateASLmtd,
        tBgpInstancePlcyImportPolicy1,
        tBgpInstancePlcyImportPolicy2,
        tBgpInstancePlcyImportPolicy3,
        tBgpInstancePlcyImportPolicy4,
        tBgpInstancePlcyImportPolicy5,
        tBgpInstancePlcyImportPolicy6,
        tBgpInstancePlcyImportPolicy7,
        tBgpInstancePlcyImportPolicy8,
        tBgpInstancePlcyImportPolicy9,
        tBgpInstancePlcyImportPolicy10,
        tBgpInstancePlcyImportPolicy11,
        tBgpInstancePlcyImportPolicy12,
        tBgpInstancePlcyImportPolicy13,
        tBgpInstancePlcyImportPolicy14,
        tBgpInstancePlcyImportPolicy15,
        tBgpInstancePlcyExportPolicy1,
        tBgpInstancePlcyExportPolicy2,
        tBgpInstancePlcyExportPolicy3,
        tBgpInstancePlcyExportPolicy4,
        tBgpInstancePlcyExportPolicy5,
        tBgpInstancePlcyExportPolicy6,
        tBgpInstancePlcyExportPolicy7,
        tBgpInstancePlcyExportPolicy8,
        tBgpInstancePlcyExportPolicy9,
        tBgpInstancePlcyExportPolicy10,
        tBgpInstancePlcyExportPolicy11,
        tBgpInstancePlcyExportPolicy12,
        tBgpInstancePlcyExportPolicy13,
        tBgpInstancePlcyExportPolicy14,
        tBgpInstancePlcyExportPolicy15
    }
    STATUS      current
    DESCRIPTION
        "The group of objects supporting management of each extended BGP
         instance on Nokia SROS series systems since release 14.0."
    ::= { tmnxBgpGroups 113 }

tmnxBgpInstanceParamsV14v0Group  OBJECT-GROUP
    OBJECTS     {
        tBgpInstanceLinkStateExEnable,
        tBgpInstanceLinkStateImEnable
    }
    STATUS      current
    DESCRIPTION
        "The group of objects supporting management of each extended BGP
         instance on Nokia SROS series systems since release 14.0."
    ::= { tmnxBgpGroups 114 }

tmnxBgpInstanceParamsV14v4Group  OBJECT-GROUP
    OBJECTS     {
        tBgpInstanceDefRxEvpnEncap
    }
    STATUS      current
    DESCRIPTION
        "The group of objects supporting management of each extended BGP
         instance on Nokia SROS series systems since release 14.0 r4."
    ::= { tmnxBgpGroups 115 }

tmnxBgpPeerGroupParamsV14v4Group OBJECT-GROUP
    OBJECTS     {
        tBgpPGDefRxEvpnEncap
    }
    STATUS      current
    DESCRIPTION
        "The group of objects supporting management of extended BGP Peer Group
         parameters on Nokia SROS series systems since release 14.0 r4."
    ::= { tmnxBgpGroups 116 }

tmnxPeerNgV15v0Group             OBJECT-GROUP
    OBJECTS     {
        tBgpPeerNgOperMcastVpnV6RecvPfxs,
        tBgpPeerNgOperMcastVpnV6ActPfxs,
        tBgpPeerNgOperMcastVpnV6RejPfxs,
        tBgpPeerNgOperMcastVpnV6SentPfxs,
        tBgpPeerNgOperMcVpnV6SuppPfxDamp
    }
    STATUS      current
    DESCRIPTION
        "The group of objects supporting management of extended BGP peers on
         Nokia SROS series systems since release 15.0."
    ::= { tmnxBgpGroups 117 }

tmnxBgpPeerParamsGroup           OBJECT-GROUP
    OBJECTS     {
        tBgpPeerNgParamsInheritance,
        tBgpPeerNgDisableFEFailover,
        tBgpPeerNgDisableComms,
        tBgpPeerNgDisableExtComms,
        tBgpPeerNgDefaultOriginate,
        tBgpPeerNgAdvertiseInactiveRts,
        tBgpPeerNgMinTTLValue,
        tBgpPeerNgTracking,
        tBgpPeerNgAuthKeyChain,
        tBgpPeerNgLastError
    }
    STATUS      current
    DESCRIPTION
        "The group of objects supporting management of each extended BGP
         parameters on Nokia SROS series systems since release 14.0 r4."
    ::= { tmnxBgpGroups 118 }

tmnxBgpPeerParamsObsoleteGroup   OBJECT-GROUP
    OBJECTS     {
        tBgpPeerNgAdvLabelAddrFamily
    }
    STATUS      current
    DESCRIPTION
        "The group of obsolete objects for BGP parameters on Nokia SROS series
         systems since release 14.0 r4."
    ::= { tmnxBgpGroups 119 }

tmnxBgpInstanceParamsV15v0Group  OBJECT-GROUP
    OBJECTS     {
        tBgpInstanceNHResolveAllowStatic,
        tBgpInstanceFSValidateDestPfx,
        tBgpInstanceFSValidateRedirectIP
    }
    STATUS      current
    DESCRIPTION
        "The group of objects supporting management of each extended BGP
         instance parameters on Nokia SROS series systems since release 15.0."
    ::= { tmnxBgpGroups 120 }

tmnxBgpLabelRtTunnelV15v0Group   OBJECT-GROUP
    OBJECTS     {
        tBgpLabelRtTunnelUdp
    }
    STATUS      current
    DESCRIPTION
        "The group of objects supporting management of BGP labeled route
         resolution using tunnels on Nokia SROS series systems since release
         15.0."
    ::= { tmnxBgpGroups 121 }

tmnxBgpORRV15v0Group             OBJECT-GROUP
    OBJECTS     {
        tBgpInstanceORRLocation,
        tBgpInstanceORRAllowLocalFallbk,
        tBgpPGORRLocation,
        tBgpPGORRAllowLocalFallbk,
        tBgpPeerNgORRLocation,
        tBgpPeerNgORRAllowLocalFallbk,
        tBgpORRSpfInitialWaitTime,
        tBgpORRSpfSecondWaitTime,
        tBgpORRSpfMaxWaitTime,
        tBgpORRPrimaryIPAddrType,
        tBgpORRPrimaryIPAddr,
        tBgpORRSecondaryIPAddrType,
        tBgpORRSecondaryIPAddr,
        tBgpORRTertiaryIPAddrType,
        tBgpORRTertiaryIPAddr,
        tBgpOptRouteReflectionTblLstCh,
        tBgpORRLocationLstCh,
        tBgpORRLocationTblLstCh,
        tBgpORRLocationRowStatus
    }
    STATUS      current
    DESCRIPTION
        "The group of objects supporting management of BGP Optimal Route
         Reflector parameters on Nokia SROS series systems since release 15.0."
    ::= { tmnxBgpGroups 122 }

tmnxBgpWeightedEcmpGroup         OBJECT-GROUP
    OBJECTS     {
        tBgpInstanceWeightedEcmp
    }
    STATUS      current
    DESCRIPTION
        "The group of objects supporting management of BGP weighted ECMP
         parameters on Nokia SROS series systems since release 15.0."
    ::= { tmnxBgpGroups 123 }

tmnxBgpObjectsV15v0ObsoleteGroup OBJECT-GROUP
    OBJECTS     {
        tBgpPGFlowspecValidate,
        tBgpPeerNgFlowspecValidate,
        tBgpInstanceFlowspecValidate,
        tBgpPGLabelResolveStatic,
        tBgpPeerNgLabelResolveStatic,
        tBgpInstanceEnableAddPath,
        tBgpInstanceRecvAddPath,
        tBgpInstanceIpv4AddPathLimit,
        tBgpInstanceVpnIpv4AddPathLimit,
        tBgpInstanceIpv6AddPathLimit,
        tBgpInstanceVpnIpv6AddPathLimit,
        tBgpInstanceLblIpv4AddPathLimit,
        tBgpInstanceLblIpv6AddPathLimit
    }
    STATUS      current
    DESCRIPTION
        "The group of obsolete objects for BGP parameters on Nokia SROS series
         systems since release 15.0."
    ::= { tmnxBgpGroups 124 }

tmnxBgpObsoleteNfyObjsV15v0Group OBJECT-GROUP
    OBJECTS     {
        tBgpFlowRouteInvalidReason,
        tBgpFlowRouteNLRI,
        tBgpPeerFlowRouteDestAddr,
        tBgpPeerFlowRouteDestAddrType
    }
    STATUS      current
    DESCRIPTION
        "The group of notify objects which are obsoleted BGP on Nokia SROS
         series systems release 15.0."
    ::= { tmnxBgpGroups 125 }

tmnxBgpObsoleteNotifyV15v0Group  NOTIFICATION-GROUP
    NOTIFICATIONS {
        tBgpFlowRouteInvalid
    }
    STATUS      current
    DESCRIPTION
        "The group of BGP notifications which are obsoleted in Nokia SROS
         series systems release 15.0."
    ::= { tmnxBgpGroups 126 }

tmnxBgpNotifyObjsV15v0Group      OBJECT-GROUP
    OBJECTS     {
        tBgp4PathAttrType,
        tBgp4PathAttrLength,
        tBgp4PathAttribute,
        tBgp4WithdrawnRoutePrefix,
        tBgp4UpdateMessage,
        tBgpFlowspecExtCommunityAction,
        tBgpFlowspecExtCommActionValue
    }
    STATUS      current
    DESCRIPTION
        "The group of notify objects supporting management of extended BGP on
         Nokia SROS series systems release 15.0."
    ::= { tmnxBgpGroups 127 }

tmnxBgpAddPathV15v0Group         OBJECT-GROUP
    OBJECTS     {
        tBgpInstanceAddPathEnable,
        tBgpInstanceAddPathRecv,
        tBgpInstanceAddPathIpv4Limit,
        tBgpInstanceAddPathVpnIpv4Limit,
        tBgpInstanceAddPathIpv6Limit,
        tBgpInstanceAddPathVpnIpv6Limit,
        tBgpInstanceAddPathLblIpv4Limit,
        tBgpInstanceAddPathLblIpv6Limit,
        tBgpInstanceAddPathTblLstCh,
        tBgpPeerNgOperBackupPrefixes,
        tBgpPeerNgOperV6BackupPrefixes,
        tBgpPeerNgAddPathRecvRemoteCaps,
        tBgpPeerNgAddPathSendRemoteCaps,
        tBgpInstanceAddPathMvpnIpv4Limit,
        tBgpInstanceAddPathMvpnIpv6Limit,
        tBgpInstanceAddPathMCVpnV4Limit,
        tBgpInstanceAddPathMCVpnV6Limit
    }
    STATUS      current
    DESCRIPTION
        "The group of objects supporting BGP ADD-PATH on Nokia SROS series
         systems release 15.0"
    ::= { tmnxBgpGroups 128 }

tmnxBgpLblRibSeparateV15v0Group  OBJECT-GROUP
    OBJECTS     {
        tBgpInstanceLabelPreference,
        tBgpPGLabelPreference,
        tBgpPeerNgLabelPreference
    }
    STATUS      current
    DESCRIPTION
        "The group of objects supporting BGP Label route property on Nokia SROS
         series systems release 15.0."
    ::= { tmnxBgpGroups 129 }

tmnxBgpEnforceFirstASGroup       OBJECT-GROUP
    OBJECTS     {
        tBgpInstanceEnforceFirstAS,
        tBgpPGEnforceFirstAS,
        tBgpPeerNgEnforceFirstAS
    }
    STATUS      current
    DESCRIPTION
        "The group of objects supporting management of BGP Enforce First AS
         parameters on Nokia SROS series systems since release 15.0 R4."
    ::= { tmnxBgpGroups 130 }

tmnxBgpInstanceParamsExtGroup    OBJECT-GROUP
    OBJECTS     {
        tBgpInstanceParamsExtTblLstCh
    }
    STATUS      current
    DESCRIPTION
        "The group of objects supporting management of each extended BGP
         instance parameters on Nokia SROS series systems since release 15.0R4."
    ::= { tmnxBgpGroups 131 }

tmnxBgpLLGRV15v0Group            OBJECT-GROUP
    OBJECTS     {
        tBgpInstanceLLGRAdvStaleTime,
        tBgpInstanceLLGROvrideStaleTime,
        tBgpInstanceLLGROvrideResTime,
        tBgpInstanceLLGRAdvStaleToNeigh,
        tBgpInstanceLLGRFwdingBitsSet,
        tBgpInstLLGRAdvToNeighWthoutNoEx,
        tBgpInstanceLLGRFamilyRowStatus,
        tBgpInstanceLLGRFamilyTblLstCh,
        tBgpInstanceLLGRFamilyLstCh,
        tBgpInstLLGRFamilyAdvStaleTime,
        tBgpInstLLGRFamilyOvrideStaleTm,
        tBgpPGLLGRAdvStaleTime,
        tBgpPGLLGROvrideStaleTime,
        tBgpPGLLGROvrideResTime,
        tBgpPGLLGRAdvStaleToNeigh,
        tBgpPGLLGRFwdingBitsSet,
        tBgpPGLLGRAdvToNeighWthoutNoEx,
        tBgpPGLLGRFamilyRowStatus,
        tBgpPGLLGRFamilyTblLstCh,
        tBgpPGLLGRFamilyLstCh,
        tBgpPGLLGRFamilyAdvStaleTime,
        tBgpPGLLGRFamilyOvrideStaleTm,
        tBgpPeerLLGRAdvStaleTime,
        tBgpPeerLLGROvrideStaleTime,
        tBgpPeerLLGROvrideResTime,
        tBgpPeerLLGRAdvStaleToNeigh,
        tBgpPeerLLGRFwdingBitsSet,
        tBgpPeerLLGRAdvToNeighWthoutNoEx,
        tBgpPeerLLGRFamilyRowStatus,
        tBgpPeerLLGRFamilyTblLstCh,
        tBgpPeerLLGRFamilyLstCh,
        tBgpPeerLLGRFamilyAdvStaleTime,
        tBgpPeerLLGRFamilyOvrideStaleTm,
        tBgpInstanceLLGR,
        tBgpPGLLGR,
        tBgpPeerLLGR,
        tBgpPeerLLGRFamilyAdvStaleTmRcv,
        tBgpPeerLLGRFamilyStaleTmNgt,
        tBgpPeerLLGRFamilyFlagsSupported,
        tBgpPeerLLGRFamilyFlagsReceived,
        tBgpPeerOperLLGRSupported,
        tBgpPeerOperLLGRFamilySupported,
        tBgpPeerOperLLGRFamilyNegotiated,
        tBgpPeerOperLLGRStatus,
        tBgpPeerOperLLGRFamilySent
    }
    STATUS      current
    DESCRIPTION
        "The group of objects supporting management of BGP Long-Lived Graceful
         Restart parameters on Nokia SROS series system since release 15.0.R4."
    ::= { tmnxBgpGroups 132 }

tmnxBgpNotificationV15v0Group    NOTIFICATION-GROUP
    NOTIFICATIONS {
        tBgp4PathAttrDiscarded
    }
    STATUS      current
    DESCRIPTION
        "The group of notifications supporting management of extended BGP on
         Nokia SROS series systems release 15.0."
    ::= { tmnxBgpGroups 133 }

tmnxBgpLocalAddressV15v4Group    OBJECT-GROUP
    OBJECTS     {
        tBgpPGLocalAddressIfName,
        tBgpPeerLocalAddressIfName
    }
    STATUS      current
    DESCRIPTION
        "The group of objects supporting management of BGP Local Address
         interface support in Nokia SROS series system since release 15.0.R4."
    ::= { tmnxBgpGroups 134 }

tmnxBgpIpv6NhAdvAndResV16v0Group OBJECT-GROUP
    OBJECTS     {
        tBgpInstanceAdvIpv6NhFamily,
        tBgpPeerGroupAdvIpv6NhFamily,
        tBgpPeerAdvIpv6NhFamily,
        tBgpInstanceExtendNhEncoding,
        tBgpPGExtendNhEncoding,
        tBgpPeerExtendNhEncoding,
        tBgpPeerRemoteExtNhEncoding
    }
    STATUS      current
    DESCRIPTION
        "The group of objects supporting management of extended BGP parameters
         on Nokia SROS series systems since release 16.0.R1."
    ::= { tmnxBgpGroups 135 }

tmnxBgpBypassMRAITimerV16v0Group OBJECT-GROUP
    OBJECTS     {
        tBgpInstanceBypassMRAITimer,
        tBgpPGBypassMRAITimer,
        tBgpPeerBypassMRAITimer
    }
    STATUS      current
    DESCRIPTION
        "The group of objects supporting management of extended BGP parameters
         on Nokia SROS series systems since release 16.0.R1."
    ::= { tmnxBgpGroups 136 }

tmnxBgpAdminTagsV16v0Group       OBJECT-GROUP
    OBJECTS     {
        tBgpShortcutTunnelAdminTags,
        tBgpLabelRtTunnelAdminTags
    }
    STATUS      current
    DESCRIPTION
        "The group of objects supporting management of extended BGP parameters
         on Nokia SROS series systems since release 16.0.R1."
    ::= { tmnxBgpGroups 137 }

tmnxPeerNgV16v0Group             OBJECT-GROUP
    OBJECTS     {
        tBgpPeerOperSrplcyV4SupPfxDamp,
        tBgpPeerOperSrplcyV4RecvPfxs,
        tBgpPeerOperSrplcyV4SentPfxs,
        tBgpPeerOperSrplcyV4ActivePfxs,
        tBgpPeerOperSrplcyV4RejPfxs
    }
    STATUS      current
    DESCRIPTION
        "The group of objects supporting management of extended BGP peers on
         Nokia SROS series systems since release 16.0."
    ::= { tmnxBgpGroups 138 }

tmnxBgpLargeCommsV16v0Group      OBJECT-GROUP
    OBJECTS     {
        tBgpPeerNgParamsExtTblLstCh,
        tBgpInstanceDisableLargeComms,
        tBgpPGDisableLargeComms,
        tBgpPeerNgParamsExtInheritanceHi,
        tBgpPeerNgParamsExtInheritanceLo,
        tBgpPeerNgDisableLargeComms
    }
    STATUS      current
    DESCRIPTION
        "The group of objects supporting management of extended BGP parameters
         on Nokia SROS series systems since release 16.0.R1."
    ::= { tmnxBgpGroups 139 }

tmnxBgpNHResFilterV16v0Group     OBJECT-GROUP
    OBJECTS     {
        tBgpLabelRtTunnelSrPolicy,
        tBgpShortcutTunnelSrPolicy,
        tBgpInstanceImportSrPolicy
    }
    STATUS      current
    DESCRIPTION
        "The group of objects supporting management of extended BGP parameters
         on Nokia SROS series systems since release 16.0.R1."
    ::= { tmnxBgpGroups 140 }

tmnxBgpPeeringPolicyV16v0Group   OBJECT-GROUP
    OBJECTS     {
        tBgpPeeringPolicyTableLastChngd,
        tBgpPrngPlcyRowStatus,
        tBgpPrngPlcyLastChngd,
        tBgpPrngPlcyDescription,
        tBgpPrngPlcyInheritance,
        tBgpPrngPlcyAdvertiseInactiveRts,
        tBgpPrngPlcyNoAggregatorID,
        tBgpPrngPlcyASOverride,
        tBgpPrngPlcyAuthKeyChain,
        tBgpPrngPlcyMd5Auth,
        tBgpPrngPlcyMd5AuthKey,
        tBgpPrngPlcyClusterId,
        tBgpPrngPlcyConnectRetry,
        tBgpPrngPlcyDampening,
        tBgpPrngPlcyDisableClientReflect,
        tBgpPrngPlcyDisableComms,
        tBgpPrngPlcyDisableExtComms,
        tBgpPrngPlcyDisableFEFailover,
        tBgpPrngPlcyHoldTime,
        tBgpPrngPlcyKeepAlive,
        tBgpPrngPlcyLocalAddressType,
        tBgpPrngPlcyLocalAddress,
        tBgpPrngPlcyLocalAS,
        tBgpPrngPlcyLocalASPrivate,
        tBgpPrngPlcyLocalPreference,
        tBgpPrngPlcyLoopDetect,
        tBgpPrngPlcyMEDSource,
        tBgpPrngPlcyMEDValue,
        tBgpPrngPlcyMinRteAdvertisement,
        tBgpPrngPlcyMultihop,
        tBgpPrngPlcyNextHopSelf,
        tBgpPrngPlcyPassive,
        tBgpPrngPlcyPeerAS,
        tBgpPrngPlcyPreference,
        tBgpPrngPlcyMaxPrefix,
        tBgpPrngPlcyRemovePrivateAS,
        tBgpPrngPlcyMinTTLValue,
        tBgpPrngPlcyPeerType,
        tBgpPeerGroupDynamicPeerGroup,
        tBgpPrngPlcyDisable4ByteASN,
        tBgpPrngPlcyRemovePrivateASLmtd
    }
    STATUS      current
    DESCRIPTION
        "The group of objects supporting management of BGP peering policies on
         Nokia SROS series systems since release 16.0."
    ::= { tmnxBgpGroups 141 }

tmnxBgpObjectsV16v0ObsoleteGroup OBJECT-GROUP
    OBJECTS     {
        tBgpPrngPlcyMinASOrigination
    }
    STATUS      current
    DESCRIPTION
        "The group of obsolete objects for BGP parameters on Nokia SROS series
         systems since release 16.0."
    ::= { tmnxBgpGroups 142 }

tmnxBgpLabelSecurityGroup        OBJECT-GROUP
    OBJECTS     {
        tBgpInstanceEnfNbrTrust
    }
    STATUS      current
    DESCRIPTION
        "The group of objects for BGP label security on Nokia SROS series
         systems since release 16.0."
    ::= { tmnxBgpGroups 143 }

tmnxBgpRibApiGroup               OBJECT-GROUP
    OBJECTS     {
        tBgpLabelRtTunnelRibApi,
        tBgpShortcutTunnelRibApi
    }
    STATUS      current
    DESCRIPTION
        "The group of objects for BGP RIB API on Nokia SROS series systems
         since release 16.0."
    ::= { tmnxBgpGroups 144 }

tmnxBgpTunnelMplsFwdPlcyGroup    OBJECT-GROUP
    OBJECTS     {
        tBgpShortcutTunnelMplsFwdPlcy,
        tBgpLabelRtTunnelMplsFwdPlcy
    }
    STATUS      current
    DESCRIPTION
        "The group of objects supporting management of BGP shortcut using
         segmented routing tunnel on Nokia  SROS series systems since release
         16.0."
    ::= { tmnxBgpGroups 145 }

tmnxBgpLinkBandwidthGroup        OBJECT-GROUP
    OBJECTS     {
        tBgpPGParamsExtTblLstCh,
        tBgpPGParamsExtInheritanceHi,
        tBgpPGParamsExtInheritanceLo,
        tBgpPGLinkAcceptEbgp,
        tBgpPGLinkSendEbgp,
        tBgpPGLinkAggPaths,
        tBgpPeerNgLinkAcceptEbgp,
        tBgpPeerNgLinkSendEbgp,
        tBgpPeerNgLinkAggPaths
    }
    STATUS      current
    DESCRIPTION
        "The group of objects supporting BGP Link Bandwidth on Nokia SROS
         series systems since release 16.0."
    ::= { tmnxBgpGroups 146 }

tmnxBgpORRV16v0Group             OBJECT-GROUP
    OBJECTS     {
        tBgpORRPrimaryIPv6AddrType,
        tBgpORRPrimaryIPv6Addr,
        tBgpORRSecondaryIPv6AddrType,
        tBgpORRSecondaryIPv6Addr,
        tBgpORRTertiaryIPv6AddrType,
        tBgpORRTertiaryIPv6Addr
    }
    STATUS      current
    DESCRIPTION
        "The group of objects supporting management of BGP Optimal Route
         Reflector parameters on Nokia SROS series systems since release 16.0."
    ::= { tmnxBgpGroups 147 }

tmnxBgpTunnelSrOspf3             OBJECT-GROUP
    OBJECTS     {
        tBgpShortcutTunnelSrOspf3,
        tBgpLabelRtTunnelSrOspf3
    }
    STATUS      current
    DESCRIPTION
        "The group of objects supporting management of BGP shortcut using
         segmented routing tunnel on Nokia  SROS series systems since release
         16.0."
    ::= { tmnxBgpGroups 148 }

tmnxBgpLoopDetectThreshold       OBJECT-GROUP
    OBJECTS     {
        tBgpInstanceLoopDetectThreshold,
        tBgpPeerNgLoopDetectThreshold,
        tBgpPGLoopDetectThreshold
    }
    STATUS      current
    DESCRIPTION
        "The group of objects supporting management of BGP loop detect
         threshold on Nokia  SROS series systems since release 16.0."
    ::= { tmnxBgpGroups 149 }

tmnxBgpNHResGroup                OBJECT-GROUP
    OBJECTS     {
        tBgpInstanceAllowUnresLeaking
    }
    STATUS      current
    DESCRIPTION
        "The group of objects extending the support of BGP Next Hop  Resolution
         functionality on Nokia SROS series systems since 19.0."
    ::= { tmnxBgpGroups 150 }

tmnxBgpConvergenceGroup          OBJECT-GROUP
    OBJECTS     {
        tBgpInstanceConvMinWaitToAdv,
        tBgpConvergenceTblLstCh,
        tBgpConvergenceFamily,
        tBgpConvergenceLstCh,
        tBgpConvergenceMaxWaitToAdv,
        tBgpPeerEORSent,
        tBgpPeerEORReceived,
        tBgpPeerConvExceededMinWait,
        tBgpConvTimerEstablishedPeers,
        tBgpConvEstablishedPeers,
        tBgpConvFirstSessEstablishedTime,
        tBgpConvLastSessEstablishedTime,
        tBgpConvergedPeers,
        tBgpConvergenceState,
        tBgpConvergenceTime,
        tBgpConvergenceOperMaxWaitToAdv
    }
    STATUS      current
    DESCRIPTION
        "The group of objects providing support for BGP convergence tracking on
         Nokia SROS series systems since 19.0."
    ::= { tmnxBgpGroups 151 }

tmnxBgpNotificationV19v0Group    NOTIFICATION-GROUP
    NOTIFICATIONS {
        tBgpInstConvStateTransition
    }
    STATUS      current
    DESCRIPTION
        "The group of objects supporting convergence  notifications on virtual
         routers for version 19.0 Nokia  SROS series systems."
    ::= { tmnxBgpGroups 152 }

tmnxBgpInstanceV19v0Group        OBJECT-GROUP
    OBJECTS     {
        tBgpInstMultipathNgRowStatus,
        tBgpInstMultipathNgLstCh,
        tBgpInstMultipathNgBgp,
        tBgpInstMultipathNgEBgp,
        tBgpInstMultipathNgIBgp,
        tBgpInstMultipathNgRestrict,
        tBgpInstMultipathNgUnequalCost,
        tBgpPGMultipathEligible,
        tBgpPeerNgMultipathEligible
    }
    STATUS      current
    DESCRIPTION
        "The group of objects supporting management of each extended BGP
         instance on Nokia SROS series systems since release 19.0."
    ::= { tmnxBgpGroups 153 }

tmnxBgpDefaultOriginate          OBJECT-GROUP
    OBJECTS     {
        tBgpInstDefOriginate,
        tBgpPGDefOriginate,
        tBgpPeerNgDefOriginate,
        tBgpInstanceSendExportPolicy,
        tBgpPGSendExportPolicy,
        tBgpPeerNgSendExportPolicy
    }
    STATUS      current
    DESCRIPTION
        "The group of objects supporting management of BGP default originate on
         Nokia  SROS series systems since release 19.0."
    ::= { tmnxBgpGroups 154 }

tBgpPeerGrpDynNbrAsGroup         OBJECT-GROUP
    OBJECTS     {
        tBgpPeerGrpDynNbrAsRngTblLstChg,
        tBgpPeerGroupDynNbrAsRangeChg,
        tBgpPeerGroupDynNbrAsRangeMin,
        tBgpPeerGroupDynNbrAsRangeMax,
        tBgpPeerOperAS4Byte
    }
    STATUS      current
    DESCRIPTION
        "The group of objects supporting management of BGP peering
         dynamic-neighbor AS range feature on SROS series systems since release
         19.0."
    ::= { tmnxBgpGroups 155 }

tmnxBgpPreferenceGroup           OBJECT-GROUP
    OBJECTS     {
        tBgpInstEbgpPreference,
        tBgpInstIbgpPreference,
        tBgpInstEbgpLabelPreference,
        tBgpInstIbgpLabelPreference,
        tBgpPGEbgpPreference,
        tBgpPGIbgpPreference,
        tBgpPGEbgpLabelPreference,
        tBgpPGIbgpLabelPreference,
        tBgpPeerNgEbgpPreference,
        tBgpPeerNgIbgpPreference,
        tBgpPeerNgEbgpLabelPreference,
        tBgpPeerNgIbgpLabelPreference,
        tBgpPeerNgOperEPreference,
        tBgpPeerNgOperIPreference,
        tBgpPeerNgOperELabelPreference,
        tBgpPeerNgOperILabelPreference
    }
    STATUS      current
    DESCRIPTION
        "The group of objects providing support for BGP ebgp ibgp preference on
         Nokia SROS series systems since 19.0."
    ::= { tmnxBgpGroups 156 }

tmnxBgpEBGPRejectWithoutPolicy   OBJECT-GROUP
    OBJECTS     {
        tBgpPeerNgEBGPRejWithoutPlcyImpt,
        tBgpPeerNgEBGPRejWithoutPlcyExpt,
        tBgpInstEBGPRejWithoutPlcyImpt,
        tBgpInstEBGPRejWithoutPlcyExpt,
        tBgpPGEBGPRejWithoutPlcyImpt,
        tBgpPGEBGPRejWithoutPlcyExpt
    }
    STATUS      current
    DESCRIPTION
        "The group of objects supporting management of BGP EBGP Reject Without
         Policy on Nokia  SROS series systems since release 19.0."
    ::= { tmnxBgpGroups 157 }

tmnxBgpRemovePrivateReplace      OBJECT-GROUP
    OBJECTS     {
        tBgpInstRemovePrivateReplaceAS,
        tBgpPGRemovePrivateReplaceAs,
        tBgpPeerNgRemovePrivateReplace
    }
    STATUS      current
    DESCRIPTION
        "The group of objects supporting management of BGP remove-private
         replace on Nokia  SROS series systems since release 19.0."
    ::= { tmnxBgpGroups 158 }

tmnxBgpBlockPrefixSIDGroup       OBJECT-GROUP
    OBJECTS     {
        tBgpInstBlockPrefixSID,
        tBgpPGBlockPrefixSID,
        tBgpPeerNgBlockPrefixSID
    }
    STATUS      current
    DESCRIPTION
        "The group of objects supporting management of BGP Block Prefix SID on
         Nokia SROS series systems since release 19.0."
    ::= { tmnxBgpGroups 159 }

tmnxPeerNgV19v5Group             OBJECT-GROUP
    OBJECTS     {
        tBgpPeerNgSelLabelIpv4Inst,
        tBgpSelLabelIpv4Inst,
        tBgpPGSelLabelIpv4Inst
    }
    STATUS      current
    DESCRIPTION
        "The group of objects supporting management of BGP on Nokia SROS series
         systems since release 19.5."
    ::= { tmnxBgpGroups 160 }

tmnxBgpNotifyObjsV19v0Group      OBJECT-GROUP
    OBJECTS     {
        tBgpOldConvergenceState,
        tBgpASN4Byte
    }
    STATUS      current
    DESCRIPTION
        "The group of notify objects supporting management of extended BGP on
         Nokia SROS series systems release 19.0."
    ::= { tmnxBgpGroups 161 }

tmnxBgpTcpMss                    OBJECT-GROUP
    OBJECTS     {
        tBgpInstTcpMss,
        tBgpPGTcpMss,
        tBgpPeerNgTcpMss,
        tBgpPeerOperTcpMss,
        tBgpPeerOperTcpRcvdMss
    }
    STATUS      current
    DESCRIPTION
        "The group of objects supporting management of BGP tcp-mss on Nokia
         SROS series systems since release 19.0."
    ::= { tmnxBgpGroups 162 }

tmnxBgpSegRoutingV19Group        OBJECT-GROUP
    OBJECTS     {
        tBgpPrefixSidRangeType,
        tBgpPrefixSidRangeStartLabel,
        tBgpPrefixSidRangeMaxIdx,
        tBgpSrAdminState,
        tBgpSegmentRouting
    }
    STATUS      current
    DESCRIPTION
        "The group of objects supporting management of BGP Segment Routing on
         Nokia SROS series systems release 19.10."
    ::= { tmnxBgpGroups 163 }

tmnxBgpSrTePolicyIpv6Group       OBJECT-GROUP
    OBJECTS     {
        tBgpPeerOperSrplcyV6SupPfxDamp,
        tBgpPeerOperSrplcyV6RecvPfxs,
        tBgpPeerOperSrplcyV6SentPfxs,
        tBgpPeerOperSrplcyV6ActivePfxs,
        tBgpPeerOperSrplcyV6RejPfxs
    }
    STATUS      current
    DESCRIPTION
        "The group of objects supporting management of extended BGP peers on
         Nokia SROS series systems since release 19."
    ::= { tmnxBgpGroups 164 }

tmnxBgpLabelIpv6V20Group         OBJECT-GROUP
    OBJECTS     {
        tBgpDisableExplicitNull
    }
    STATUS      current
    DESCRIPTION
        "The group of objects supporting management of extended BGP disable
         explicit null on Nokia SROS series systems since release 20."
    ::= { tmnxBgpGroups 165 }

tmnxBgpTunnelMetric              OBJECT-GROUP
    OBJECTS     {
        tBgpInstBgpTunnelMetric,
        tBgpInstBgpTunnelMetricPrefAigp
    }
    STATUS      current
    DESCRIPTION
        ""
    ::= { tmnxBgpGroups 166 }

tmnxBgpEngressEng                OBJECT-GROUP
    OBJECTS     {
        tBgpEgressEng,
        tBgpEgressEngShutdown,
        tBgpPGEgressEng,
        tBgpPGEgressEngShutdown,
        tBgpPeerNgEgressEng,
        tBgpPeerNgEgressEngShutdown,
        tBgpPeerNgNodeSid,
        tBgpPeerNgNodeSidStatsPktCnt,
        tBgpPeerNgNodeSidStatsByteCnt,
        tBgpPeerNgAdjSid1Value,
        tBgpPeerNgAdjSid1StatsPktCnt,
        tBgpPeerNgAdjSid1StatsByteCnt,
        tBgpPeerNgAdjSid2Value,
        tBgpPeerNgAdjSid2StatsPktCnt,
        tBgpPeerNgAdjSid2StatsByteCnt,
        tBgpPeerNgAdjSid3Value,
        tBgpPeerNgAdjSid3StatsPktCnt,
        tBgpPeerNgAdjSid3StatsByteCnt,
        tBgpPeerNgAdjSid4Value,
        tBgpPeerNgAdjSid4StatsPktCnt,
        tBgpPeerNgAdjSid4StatsByteCnt,
        tBgpPeerNgAdjSid5Value,
        tBgpPeerNgAdjSid5StatsPktCnt,
        tBgpPeerNgAdjSid5StatsByteCnt,
        tBgpPeerNgAdjSid6Value,
        tBgpPeerNgAdjSid6StatsPktCnt,
        tBgpPeerNgAdjSid6StatsByteCnt,
        tBgpPeerNgAdjSid7Value,
        tBgpPeerNgAdjSid7StatsPktCnt,
        tBgpPeerNgAdjSid7StatsByteCnt,
        tBgpPeerNgAdjSid8Value,
        tBgpPeerNgAdjSid8StatsPktCnt,
        tBgpPeerNgAdjSid8StatsByteCnt,
        tBgpPeerNgAdjSid9Value,
        tBgpPeerNgAdjSid9StatsPktCnt,
        tBgpPeerNgAdjSid9StatsByteCnt,
        tBgpPeerNgAdjSid10Value,
        tBgpPeerNgAdjSid10StatsPktCnt,
        tBgpPeerNgAdjSid10StatsByteCnt,
        tBgpPeerNgAdjSid11Value,
        tBgpPeerNgAdjSid11StatsPktCnt,
        tBgpPeerNgAdjSid11StatsByteCnt,
        tBgpPeerNgAdjSid12Value,
        tBgpPeerNgAdjSid12StatsPktCnt,
        tBgpPeerNgAdjSid12StatsByteCnt,
        tBgpPeerNgAdjSid13Value,
        tBgpPeerNgAdjSid13StatsPktCnt,
        tBgpPeerNgAdjSid13StatsByteCnt,
        tBgpPeerNgAdjSid14Value,
        tBgpPeerNgAdjSid14StatsPktCnt,
        tBgpPeerNgAdjSid14StatsByteCnt,
        tBgpPeerNgAdjSid15Value,
        tBgpPeerNgAdjSid15StatsPktCnt,
        tBgpPeerNgAdjSid15StatsByteCnt,
        tBgpPeerNgAdjSid16Value,
        tBgpPeerNgAdjSid16StatsPktCnt,
        tBgpPeerNgAdjSid16StatsByteCnt,
        tBgpPeerNgAdjSid17Value,
        tBgpPeerNgAdjSid17StatsPktCnt,
        tBgpPeerNgAdjSid17StatsByteCnt,
        tBgpPeerNgAdjSid18Value,
        tBgpPeerNgAdjSid18StatsPktCnt,
        tBgpPeerNgAdjSid18StatsByteCnt,
        tBgpPeerNgAdjSid19Value,
        tBgpPeerNgAdjSid19StatsPktCnt,
        tBgpPeerNgAdjSid19StatsByteCnt,
        tBgpPeerNgAdjSid20Value,
        tBgpPeerNgAdjSid20StatsPktCnt,
        tBgpPeerNgAdjSid20StatsByteCnt,
        tBgpPeerNgAdjSid21Value,
        tBgpPeerNgAdjSid21StatsPktCnt,
        tBgpPeerNgAdjSid21StatsByteCnt,
        tBgpPeerNgAdjSid22Value,
        tBgpPeerNgAdjSid22StatsPktCnt,
        tBgpPeerNgAdjSid22StatsByteCnt,
        tBgpPeerNgAdjSid23Value,
        tBgpPeerNgAdjSid23StatsPktCnt,
        tBgpPeerNgAdjSid23StatsByteCnt,
        tBgpPeerNgAdjSid24Value,
        tBgpPeerNgAdjSid24StatsPktCnt,
        tBgpPeerNgAdjSid24StatsByteCnt,
        tBgpPeerNgAdjSid25Value,
        tBgpPeerNgAdjSid25StatsPktCnt,
        tBgpPeerNgAdjSid25StatsByteCnt,
        tBgpPeerNgAdjSid26Value,
        tBgpPeerNgAdjSid26StatsPktCnt,
        tBgpPeerNgAdjSid26StatsByteCnt,
        tBgpPeerNgAdjSid27Value,
        tBgpPeerNgAdjSid27StatsPktCnt,
        tBgpPeerNgAdjSid27StatsByteCnt,
        tBgpPeerNgAdjSid28Value,
        tBgpPeerNgAdjSid28StatsPktCnt,
        tBgpPeerNgAdjSid28StatsByteCnt,
        tBgpPeerNgAdjSid29Value,
        tBgpPeerNgAdjSid29StatsPktCnt,
        tBgpPeerNgAdjSid29StatsByteCnt,
        tBgpPeerNgAdjSid30Value,
        tBgpPeerNgAdjSid30StatsPktCnt,
        tBgpPeerNgAdjSid30StatsByteCnt,
        tBgpPeerNgAdjSid31Value,
        tBgpPeerNgAdjSid31StatsPktCnt,
        tBgpPeerNgAdjSid31StatsByteCnt,
        tBgpPeerNgAdjSid32Value,
        tBgpPeerNgAdjSid32StatsPktCnt,
        tBgpPeerNgAdjSid32StatsByteCnt
    }
    STATUS      current
    DESCRIPTION
        "The group of objects supporting management of BGP egress engineering
         on Nokia SROS series systems since release 20.0."
    ::= { tmnxBgpGroups 168 }

tmnxBgpNHV20v0Group              OBJECT-GROUP
    OBJECTS     {
        tBgpInstanceNHResVpnFamPolicy
    }
    STATUS      current
    DESCRIPTION
        "The group of objects supporting management of BGP next-hop-resolution
         policy feature on SROS series systems since release 20.0."
    ::= { tmnxBgpGroups 169 }

tmnxBgpLRV20v0Group              OBJECT-GROUP
    OBJECTS     {
        tBgpPeerOperLocalAddress,
        tBgpPeerOperRemoteAddressType,
        tBgpPeerOperLocalAddressType,
        tBgpPeerOperRemoteAddress
    }
    STATUS      current
    DESCRIPTION
        "The group of objects supporting management of BGP local address and
         remote address IPv6 objects on SROS series systems."
    ::= { tmnxBgpGroups 170 }

tmnxBgpTunnelFlexAlgoFb          OBJECT-GROUP
    OBJECTS     {
        tBgpShortcutTunnelFlexAlgoFb,
        tBgpLabelRtTunnelFlexAlgoFb
    }
    STATUS      current
    DESCRIPTION
        ""
    ::= { tmnxBgpGroups 171 }

tmnxBgpLUStats                   OBJECT-GROUP
    OBJECTS     {
        tBgpLUStatsTblLstCh,
        tBgpLUStatsFamily,
        tBgpLUStatsPrefixType,
        tBgpLUStatsPrefix,
        tBgpLUStatsPrefixLength,
        tBgpLUStatsLstCh,
        tBgpLUStatsNextHopType,
        tBgpLUStatsNextHopAddress,
        tBgpLUStatsIngressOperState,
        tBgpLUStatsIngressLabel,
        tBgpLUIngressStatsPktCnt,
        tBgpLUIngressStatsOctetsCnt,
        tBgpLUStatsEgressOperState,
        tBgpLUStatsEgressLabel,
        tBgpLUEgressStatsPktCnt,
        tBgpLUEgressStatsOctetsCnt
    }
    STATUS      current
    DESCRIPTION
        ""
    ::= { tmnxBgpGroups 172 }

tmnxBgpTunnelPreference          OBJECT-GROUP
    OBJECTS     {
        tBgpInstBgpTunnelPreference
    }
    STATUS      current
    DESCRIPTION
        ""
    ::= { tmnxBgpGroups 174 }

tmnxBgpLabelRoutesUseBgpRoutes   OBJECT-GROUP
    OBJECTS     {
        tBgpInstLabelIpv6ExplicitNull
    }
    STATUS      current
    DESCRIPTION
        ""
    ::= { tmnxBgpGroups 175 }

tmnxBgpSrv6                      OBJECT-GROUP
    OBJECTS     {
        tBgpSegmentRoutingV6,
        tBgpSrv6TblLstCh,
        tBgpSrv6LstCh,
        tBgpSrv6RowStatus,
        tBgpSrv6AddTlv,
        tBgpSrv6LocatorName,
        tBgpSrv6IgRecvTlv,
        tBgpInstSrv6SourceAddrType,
        tBgpInstSrv6SourceAddr
    }
    STATUS      current
    DESCRIPTION
        ""
    ::= { tmnxBgpGroups 176 }

tmnxBgpGlobalV21v0Group          OBJECT-GROUP
    OBJECTS     {
        tBgpPrngPlcyBfdEnable
    }
    STATUS      current
    DESCRIPTION
        "The group of objects supporting management of BFD for dynamic BGP
         sessions feature on SROS series systems since release 21.0."
    ::= { tmnxBgpGroups 177 }

tmnxBgpSubconfVpnFwding          OBJECT-GROUP
    OBJECTS     {
        tBgpInstanceSubconfVpnFwding
    }
    STATUS      current
    DESCRIPTION
        ""
    ::= { tmnxBgpGroups 178 }

tmnxBgpSelLblIpPri               OBJECT-GROUP
    OBJECTS     {
        tBgpInstanceSelLblIpPri
    }
    STATUS      current
    DESCRIPTION
        "The group of objects supporting management of selective label ip
         prioritization feature on SROS series systems since release 21.10."
    ::= { tmnxBgpGroups 179 }

tmnxBgpEvpnAddPaths              OBJECT-GROUP
    OBJECTS     {
        tBgpInstanceAddPathEvpnLimit
    }
    STATUS      current
    DESCRIPTION
        ""
    ::= { tmnxBgpGroups 180 }

tmnxBgpSrv6Tlv                   OBJECT-GROUP
    OBJECTS     {
        tBgpPGSegmentRoutingV6,
        tBgpPGSrv6RouteAdvertisement,
        tBgpPGSrv6DropRoutes,
        tBgpPGSrv6TblLstCh,
        tBgpPGSrv6RowStatus,
        tBgpPGSrv6LstCh,
        tBgpPGSrv6StripTlv,
        tBgpPeerNgSegmentRoutingV6,
        tBgpPeerNgSrv6RouteAdvertisement,
        tBgpPeerNgSrv6DropRoutes,
        tBgpPeerNgSrv6TblLstCh,
        tBgpPeerNgSrv6RowStatus,
        tBgpPeerNgSrv6LstCh,
        tBgpPeerNgSrv6StripTlv
    }
    STATUS      current
    DESCRIPTION
        ""
    ::= { tmnxBgpGroups 181 }

tmnxBgpDpath                     OBJECT-GROUP
    OBJECTS     {
        tBgpInstanceDomainId,
        tBgpInstanceDpathLgthIgnr
    }
    STATUS      obsolete
    DESCRIPTION
        "The group of objects supporting D-Path Attribute for routes
         advertisement for Release 21 on Nokia SROS series systems."
    ::= { tmnxBgpGroups 182 }

tmnxBgpNHPreferTransportFRR      OBJECT-GROUP
    OBJECTS     {
        tBgpInstanceNHPreferTransportFrr
    }
    STATUS      current
    DESCRIPTION
        ""
    ::= { tmnxBgpGroups 183 }

tmnxBgpFlowSpecVpn               OBJECT-GROUP
    OBJECTS     {
        tBgpPeerNgOperFVIpv4SupPfxDamp,
        tBgpPeerNgOperFVIpv4RecvPfxs,
        tBgpPeerNgOperFVIpv4SentPfxs,
        tBgpPeerNgOperFVIpv4ActivePfxs,
        tBgpPeerNgOperFVIpv4RejPfxs,
        tBgpPeerNgOperFVIpv6SupPfxDamp,
        tBgpPeerNgOperFVIpv6RecvPfxs,
        tBgpPeerNgOperFVIpv6SentPfxs,
        tBgpPeerNgOperFVIpv6ActivePfxs,
        tBgpPeerNgOperFVIpv6RejPfxs
    }
    STATUS      current
    DESCRIPTION
        ""
    ::= { tmnxBgpGroups 184 }

tmnxBgpAddPathV22v2Group         OBJECT-GROUP
    OBJECTS     {
        tBgpPGAddPathInheritance,
        tBgpPGAddPathRecv,
        tBgpPGAddPathRowStatus,
        tBgpPGAddPathIpv4Limit,
        tBgpPGAddPathVpnIpv4Limit,
        tBgpPGAddPathLblIpv4Limit,
        tBgpPGAddPathLblIpv6Limit,
        tBgpPGAddPathIpv6Limit,
        tBgpPGAddPathVpnIpv6Limit,
        tBgpPGAddPathMvpnIpv4Limit,
        tBgpPGAddPathMvpnIpv6Limit,
        tBgpPGAddPathMcastVpnV4Limit,
        tBgpPGAddPathMcastVpnV6Limit,
        tBgpPGAddPathEvpnLimit,
        tBgpPeerGroupAddPathTblLstCh,
        tBgpPeerGroupAddPathLstCh,
        tBgpPeerNgAddPathEvpnLimit,
        tBgpPeerNgAddPathIpv4Limit,
        tBgpPeerNgAddPathIpv6Limit,
        tBgpPeerNgAddPathLblIpv4Limit,
        tBgpPeerNgAddPathLblIpv6Limit,
        tBgpPeerNgAddPathMcastVpnV4Limit,
        tBgpPeerNgAddPathMcastVpnV6Limit,
        tBgpPeerNgAddPathMvpnIpv4Limit,
        tBgpPeerNgAddPathMvpnIpv6Limit,
        tBgpPeerNgAddPathRecv,
        tBgpPeerNgAddPathVpnIpv4Limit,
        tBgpPeerNgAddPathVpnIpv6Limit,
        tBgpPeerNgAddPathsLstCh,
        tBgpPeerNgAddPathsRowStatus,
        tBgpPeerNgAddPathsTblLstCh,
        tBgpPeerNgAddPathInheritance
    }
    STATUS      current
    DESCRIPTION
        ""
    ::= { tmnxBgpGroups 185 }

tmnxBgpEPEBgpLUV22v0Group        OBJECT-GROUP
    OBJECTS     {
        tBgpPGEgressPeerEngLabelUnicast,
        tBgpPeerNgEgrPeerEngLabelUnicast
    }
    STATUS      current
    DESCRIPTION
        "The group of objects supporting labeled unicast of bgp
         egress-engineering for Release 22 on Nokia SROS series systems."
    ::= { tmnxBgpGroups 186 }

tmnxBgpObjectsV22v2ObsoleteGroup OBJECT-GROUP
    OBJECTS     {
        tBgpPGEnableAddPath,
        tBgpPGRecvAddPath,
        tBgpPGIpv4AddPathLimit,
        tBgpPGVpnIpv4AddPathLimit,
        tBgpPGIpv6AddPathLimit,
        tBgpPGVpnIpv6AddPathLimit,
        tBgpPGLblIpv4AddPathLimit,
        tBgpPGLblIpv6AddPathLimit,
        tBgpPGMvpnIpv4AddPathLimit,
        tBgpPGMvpnIpv6AddPathLimit,
        tBgpPGMcastVpnV4AddPathLimit,
        tBgpPGMcastVpnV6AddPathLimit,
        tBgpPGEvpnAddPathLimit,
        tBgpPeerNgEnableAddPath,
        tBgpPeerNgRecvAddPath,
        tBgpPeerNgIpv4AddPathLimit,
        tBgpPeerNgVpnIpv4AddPathLimit,
        tBgpPeerNgIpv6AddPathLimit,
        tBgpPeerNgVpnIpv6AddPathLimit,
        tBgpPeerNgLblIpv4AddPathLimit,
        tBgpPeerNgLblIpv6AddPathLimit,
        tBgpPeerNgMvpnIpv4AddPathLimit,
        tBgpPeerNgMvpnIpv6AddPathLimit,
        tBgpPeerNgMcastVpnV4AddPathLimit,
        tBgpPeerNgMcastVpnV6AddPathLimit,
        tBgpPeerNgEvpnAddPathLimit
    }
    STATUS      current
    DESCRIPTION
        "The group of obsolete objects for BGP parameters on Nokia SROS series
         systems since release 22.2."
    ::= { tmnxBgpGroups 188 }

tmnxBgpTunnelMetricPrefMed       OBJECT-GROUP
    OBJECTS     {
        tBgpInstBgpTunnelMetricPrefMed
    }
    STATUS      current
    DESCRIPTION
        ""
    ::= { tmnxBgpGroups 190 }

tmnxBgpPGDynNbrIfGroup           OBJECT-GROUP
    OBJECTS     {
        tBgpPGDynNbrIfTableLstChgd,
        tBgpPGDynNbrIfLastChanged,
        tBgpPGDynNbrIfRowStatus,
        tBgpPGDynNbrIfGroupName,
        tBgpPGDynNbrIfMaxSessions,
        tBgpPGDynNbrIfAsRgTblLstChg,
        tBgpPGDynNbrIfAsRangeLstChg,
        tBgpPGDynNbrIfAsRangeMin,
        tBgpPGDynNbrIfAsRangeMax
    }
    STATUS      current
    DESCRIPTION
        "The group of objects supporting bgp group dynamic neighbor  interfaces
         on Nokia SROS series system."
    ::= { tmnxBgpGroups 191 }

tmnxBgpSrv6PolicyGroup           OBJECT-GROUP
    OBJECTS     {
        tBgpSrv6Resolution
    }
    STATUS      current
    DESCRIPTION
        "The group of BGP objects supporting segment routing v6 policy  on
         Nokia SROS series system."
    ::= { tmnxBgpGroups 192 }

tmnxBgpPGDynNbrIfMaxSessNtfnGrp  NOTIFICATION-GROUP
    NOTIFICATIONS {
        tBgpPGDynNbrIfMaxSessLmtReachd
    }
    STATUS      current
    DESCRIPTION
        "The group of objects supporting bgp group dynamic neighbor interface
         max-sessions notifications on Nokia SROS series systems."
    ::= { tmnxBgpGroups 193 }

tmnxBgpEvpnLinkBWGroup           OBJECT-GROUP
    OBJECTS     {
        tBgpPGEvpnLinkBWAddToRcvdBgp,
        tBgpPeerNgEvpnLinkBWAddToRcvdBgp
    }
    STATUS      current
    DESCRIPTION
        "The group of objects supporting bgp evpn-link-bandwidth on Nokia SROS
         series system."
    ::= { tmnxBgpGroups 194 }

tmnxBgpPeerFsmTimeGroup          OBJECT-GROUP
    OBJECTS     {
        tBgpPeerFsmEstablishedTime
    }
    STATUS      current
    DESCRIPTION
        "The group of BGP objects supporting bgp4-mib objects  on Nokia SROS
         series system."
    ::= { tmnxBgpGroups 195 }

tmnxBgpSrv6MicroSegmentGroup     OBJECT-GROUP
    OBJECTS     {
        tBgpSrv6MSLocatorName
    }
    STATUS      current
    DESCRIPTION
        "The group of objects supporting segment routing v6 micro segment on
         SROS series system."
    ::= { tmnxBgpGroups 197 }

tmnxBgpSelLabelIpInstallGroup    OBJECT-GROUP
    OBJECTS     {
        tBgpInstanceSelLabelIp
    }
    STATUS      current
    DESCRIPTION
        "The group of objects supporting selective label ip install for BGP-LU
         routes on Nokia SROS series system."
    ::= { tmnxBgpGroups 198 }

tmnxBgpBfdStrictMode             OBJECT-GROUP
    OBJECTS     {
        tBgpInstanceBfdStrictAdvertise,
        tBgpInstanceBfdStrictNhReach,
        tBgpInstanceBfdStrictHoldTime,
        tBgpPGBfdStrictAdvertise,
        tBgpPGBfdStrictNhReach,
        tBgpPGBfdStrictHoldTime,
        tBgpPeerNgBfdStrictAdvertise,
        tBgpPeerNgBfdStrictNhReach,
        tBgpPeerNgBfdStrictHoldTime
    }
    STATUS      current
    DESCRIPTION
        "The group of objects supporting strict mode BFD for BGP sessions on
         Nokia SROS series system."
    ::= { tmnxBgpGroups 199 }

tmnxBgpGlobalV23v0Group          OBJECT-GROUP
    OBJECTS     {
        tBgpPrngPlcyFamilyIpv4,
        tBgpPrngPlcyFamilyIpv6,
        tBgpPrngPlcyPfxLmtTableLastChngd,
        tBgpPrngPlcyPfxLmtLastChanged,
        tBgpPrngPlcyPfxLmtRowStatus,
        tBgpPrngPlcyPfxLmtMaxPrefix,
        tBgpPrngPlcyPfxLmtLogOnly,
        tBgpPrngPlcyPfxLmtThreshold,
        tBgpPrngPlcyPfxLmtIdleTimeOut,
        tBgpPrngPlcyPfxLmtPostImport
    }
    STATUS      current
    DESCRIPTION
        "The group of objects supporting management of dynamic BGP sessions on
         SROS series systems added in release 23."
    ::= { tmnxBgpGroups 200 }

tmnxBgpLeakedRoutesStaticGroup   OBJECT-GROUP
    OBJECTS     {
        tBgpUseLeakedRoutesTblLstCh,
        tBgpUseLeakedRoutesStatic
    }
    STATUS      current
    DESCRIPTION
        "The group of objects supporting BGP route resolution using leaked
         static routes."
    ::= { tmnxBgpGroups 202 }

tmnxBgpPfxLmtHoldExcessGroup     OBJECT-GROUP
    OBJECTS     {
        tBgpPeerGroupPfxLmtHoldExcess,
        tBgpPeerNgPfxLmtHoldExcess,
        tBgpPeerAFStatsHeldExcessPfxs
    }
    STATUS      current
    DESCRIPTION
        "The group of objects supporting BGP prefix-limt hold-excess on Nokia
         SROS series system."
    ::= { tmnxBgpGroups 203 }

tmnxBgpAttrSetGroup              OBJECT-GROUP
    OBJECTS     {
        tBgpInstanceAttrSetRemove
    }
    STATUS      current
    DESCRIPTION
        "The group of objects supporting VPRN BGP ATTR_SET group on Nokia SROS
         series system."
    ::= { tmnxBgpGroups 207 }

tmnxBgpEnforceUntagRtGroup       OBJECT-GROUP
    OBJECTS     {
        tBgpShortcutTunnelEnforceUntagRt,
        tBgpLabelRtTunnelEnforceUntagRt
    }
    STATUS      current
    DESCRIPTION
        "The group of objects supporting BGP next-hop-resolution
         enforce-untagged-route on Nokia SROS series system."
    ::= { tmnxBgpGroups 208 }

tmnxBgpLegacyFaultToleranceGroup OBJECT-GROUP
    OBJECTS     {
        tBgpInstLegacyFaultTolerance
    }
    STATUS      current
    DESCRIPTION
        "The group of objects supporting BGP error-handling legacy-mode on
         Nokia SROS series system."
    ::= { tmnxBgpGroups 209 }

tBgpSrv6UpaTriggerNextHopGroup   OBJECT-GROUP
    OBJECTS     {
        tBgpSrv6UpaTriggerNextHop
    }
    STATUS      current
    DESCRIPTION
        "The group of objects supporting BGP Unreachable Prefix
         Announcement(UPA) trigger for next-hop on Nokia SROS series system."
    ::= { tmnxBgpGroups 210 }

tmnxBgpLUEcmpGroup               OBJECT-GROUP
    OBJECTS     {
        tBgpLabelRtTunnelMaxEcmpRoutes
    }
    STATUS      current
    DESCRIPTION
        "The group of objects supporting BGP-LU ECMP on Nokia SROS series
         system."
    ::= { tmnxBgpGroups 216 }

tmnxBgpPeerNgOperSRLGroup        OBJECT-GROUP
    OBJECTS     {
        tBgpPeerNgOperLastError,
        tBgpPeerNgOperLocalPort,
        tBgpPeerNgOperRemotePort,
        tBgpPeerNgOperIdentifier,
        tBgpPeerNgOperInUpdates,
        tBgpPeerNgOperOutUpdates,
        tBgpPeerNgOperInTotalMessages,
        tBgpPeerNgOperOutTotalMessages,
        tBgpPeerNgOperInNotifications,
        tBgpPeerNgOperOutNotifications,
        tBgpPeerNgOperInUpdElapsedTime
    }
    STATUS      current
    DESCRIPTION
        "The group of BGP objects supporting bgp4-mib objects  on Nokia SRLINUX
         series system."
    ::= { tmnxBgpGroups 217 }

tmnxBgpDpath25v0                 OBJECT-GROUP
    OBJECTS     {
        tBgpInstanceDpathLgthIgnr
    }
    STATUS      current
    DESCRIPTION
        "The group of objects supporting D-Path Attribute for routes
         advertisement for Release 25 on Nokia SROS series systems."
    ::= { tmnxBgpGroups 223 }

tmnxBgpDpathObsoleteGroup        OBJECT-GROUP
    OBJECTS     {
        tBgpInstanceDomainId
    }
    STATUS      current
    DESCRIPTION
        "The group of D-path objects obsoleted in release 25.3 on Nokia SROS
         series system."
    ::= { tmnxBgpGroups 224 }

tBgpNotificationsPrefix          OBJECT IDENTIFIER ::= { tmnxSRNotifyPrefix 14 }

tBgpNotifications                OBJECT IDENTIFIER ::= { tBgpNotificationsPrefix 0 }

tBgpMaxPrefix90                  NOTIFICATION-TYPE
    OBJECTS     {
        tBgpPeerMaxPrefix
    }
    STATUS      obsolete
    DESCRIPTION
        "the number of routes learned from this peer has exceeded 90 percent of
         the configured maximum."
    ::= { tBgpNotifications 1 }

tBgpMaxPrefix100                 NOTIFICATION-TYPE
    OBJECTS     {
        tBgpPeerMaxPrefix
    }
    STATUS      obsolete
    DESCRIPTION
        "the number of routes learned from this peer has exceeded the
         configured maximum."
    ::= { tBgpNotifications 2 }

tBgpPeerGRStatusChange           NOTIFICATION-TYPE
    OBJECTS     {
        tBgpPeerOperGRStatus,
        tBgpASN4Byte
    }
    STATUS      obsolete
    DESCRIPTION
        "The tBgpPeerGRStatusChange notification is generated when the graceful
         restart status changes for a BGP peer."
    ::= { tBgpNotifications 3 }

tBgpMaxNgPrefix90                NOTIFICATION-TYPE
    OBJECTS     {
        tBgpPeerNgMaxPrefix,
        tBgpPeerNgMaxPrefixThreshold
    }
    STATUS      obsolete
    DESCRIPTION
        "A tBgpMaxNgPrefix90 notification is generated when the number of
         routes learned from the peer has exceeded tBgpPeerNgMaxPrefixThreshold
         percent of the configured maximum (tBgpPeerNgMaxPrefix).
         tBgpMaxNgPrefix90 replaces notification object tBgpMaxPrefix90 as the
         latter does not support an IPv6 peer."
    ::= { tBgpNotifications 4 }

tBgpMaxNgPrefix100               NOTIFICATION-TYPE
    OBJECTS     {
        tBgpPeerNgMaxPrefix
    }
    STATUS      obsolete
    DESCRIPTION
        "A tBgpMaxNgPrefix100 notification is generated when the number of
         routes learned from the peer has exceeded the configured maximum.
         tBgpMaxNgPrefix100 replaces notification object tBgpMaxPrefix100 as
         the latter does not support an IPv6 peer.

         This notification is obsoleted in release 13.0."
    ::= { tBgpNotifications 5 }

tBgpPeerNgGRStatusChange         NOTIFICATION-TYPE
    OBJECTS     {
        tBgpPeerNgOperGRStatus
    }
    STATUS      current
    DESCRIPTION
        "A tBgpPeerNgGRStatusChange notification is generated when the graceful
         restart status changes for a BGP peer. tBgpPeerNgGRStatusChange
         replaces notification object tBgpPeerGRStatusChange as the latter does
         not support an IPv6 peer."
    ::= { tBgpNotifications 6 }

tBgpNgEstablished                NOTIFICATION-TYPE
    OBJECTS     {
        tBgpPeerNgLastError,
        tBgpPeerNgConnState,
        tBgpASN4Byte
    }
    STATUS      current
    DESCRIPTION
        "A tBgpNgEstablished notification is generated when the BGP FSM enters
         the ESTABLISHED state.

         tBgpNgEstablished is only generated for ipv6 addresses.
         BGP4-MIB::bgpEstablished is generated for ipv4 addresses."
    ::= { tBgpNotifications 7 }

tBgpNgBackwardTransition         NOTIFICATION-TYPE
    OBJECTS     {
        tBgpPeerNgLastError,
        tBgpPeerNgConnState,
        tBgpASN4Byte
    }
    STATUS      current
    DESCRIPTION
        "A tBgpNgBackwardTransition notification is generated when the BGP FSM
         moves from a higher numbered state to a lower numbered state.

         tBgpNgBackwardTransition is only generated for ipv6 addresses.
         BGP4-MIB::bgpBackwardTransition is generated for ipv4 addresses."
    ::= { tBgpNotifications 8 }

tBgpPeerNgHoldTimeInconsistent   NOTIFICATION-TYPE
    OBJECTS     {
        tBgpPeerNgHoldTime,
        tBgpPeerNgAddrType,
        tBgpPeerNgAddr,
        tBgpPeerNgMinHoldTime,
        tBgpASN4Byte
    }
    STATUS      current
    DESCRIPTION
        "A tBgpPeerNgHoldTimeInconsistent notification is generated for a BGP
         neighbor when a peer tries to establish a peering with a hold time
         less than the configured minimum hold time. The peering would be
         rejected."
    ::= { tBgpNotifications 9 }

tBgpFlowspecUnsupportdComAction  NOTIFICATION-TYPE
    OBJECTS     {
        tBgpFlowspecExtCommunityAction,
        tBgpFlowspecExtCommActionValue,
        tBgpASN4Byte
    }
    STATUS      current
    DESCRIPTION
        "[CAUSE] The tBgpFlowspecUnsupportdComAction notification is generated
         when the best route for a flow specification NLRI (Network Layer
         Reachability Information) is received from a remote BGP peer with an
         extended community action that is unsupported.

         [EFFECT] The BGP peer dose not create an ip filter entry for the
         received flow route even if the NLRI (Network Layer Reachability
         Information) has valid extended community actions.

         [RECOVERY] There is no recovery required for this notification."
    ::= { tBgpNotifications 10 }

tBgpFlowRouteInvalid             NOTIFICATION-TYPE
    OBJECTS     {
        tBgpPeerNgAddrType,
        tBgpPeerNgAddr,
        tBgpPeerFlowRouteDestAddrType,
        tBgpPeerFlowRouteDestAddr,
        tBgpFlowRouteInvalidReason,
        tBgpFlowRouteNLRI
    }
    STATUS      obsolete
    DESCRIPTION
        "[CAUSE] The tBgpFlowRouteInvalid notification is generated when the
         received BGP flow route is invalid.

         [EFFECT] The BGP peer dose not create ip filter entry for the received
         flow route.

         [RECOVERY] There is no recovery required for this notification.

         This notification was obsoleted in release 15.0."
    ::= { tBgpNotifications 11 }

tBgpMaxNgPrefixThreshReached     NOTIFICATION-TYPE
    OBJECTS     {
        tBgpPeerNgMaxPrefix,
        tBgpPeerNgMaxPrefixThreshold
    }
    STATUS      obsolete
    DESCRIPTION
        "[CAUSE] A tBgpMaxNgPrefixThreshReached notification is generated when
         the number of routes learned from the peer has exceeded
         tBgpPeerNgMaxPrefixThreshold percent of the configured maximum
         (tBgpPeerNgMaxPrefix). tBgpMaxNgPrefixThreshReached replaces
         notification object tBgpMaxNgPrefix90 as the latter limits the
         threshold to 90 percent.

         [EFFECT] No direct effect but if the peer continues to advertise more
         routes then the number of routes may exceed the configured maximum
         (tBgpPeerNgMaxPrefix). in that case the peer would just be disabled.

         [RECOVERY] Increase the max-prefix for this peer.

         This notification is obsoleted in release 13.0."
    ::= { tBgpNotifications 12 }

tBgp4OptTransPathAttrInvalid     NOTIFICATION-TYPE
    OBJECTS     {
        vRtrID,
        tBgpPeerNgAddrType,
        tBgpPeerNgAddr,
        tBgp4OptTransPathAttrType,
        tBgp4OptTransPathAttrLength,
        tBgp4OptTransPathAttribute
    }
    STATUS      obsolete
    DESCRIPTION
        "[CAUSE] The tBgp4OptTransPathAttrInvalid notification is generated
         when the received optional-transitive path attribute is unknown to
         this BGP peer.

         This notification was obsoleted in R11.0 and replaced with the
         notification tBgp4PathAttrInvalid.

         [EFFECT] The BGP peer simply passes the path attribute to the next BGP
         peer along the route and is not considered responsible for any
         encoding error. In this case the BGP peering is not torn down.

         [RECOVERY] There is no recovery required for this notification."
    ::= { tBgpNotifications 13 }

tBgp4OptTransWithdrawnRoutes     NOTIFICATION-TYPE
    OBJECTS     {
        vRtrID,
        tBgpPeerNgAddrType,
        tBgpPeerNgAddr,
        tBgp4OTWithdrawnRouteLength,
        tBgp4OTWithdrawnRoutePrefix
    }
    STATUS      obsolete
    DESCRIPTION
        "[CAUSE] The tBgp4OptTransWithdrawnRoutes notification is generated
         when the processing of optional-transitive path attribute results in
         the withdrawal of the routes included in the BGP update.

         This notification was obsoleted in R11.0 and replaced with the
         notification tBgp4WithdrawnRtFromUpdateError.

         [EFFECT] This notification has no direct effect. The withdrawn routes
         are logged to aid debugging and tracking back the root cause of the
         problem.

         [RECOVERY] There is no recovery required for this notification."
    ::= { tBgpNotifications 14 }

tBgp4RouteInvalid                NOTIFICATION-TYPE
    OBJECTS     {
        vRtrID,
        tBgpPeerNgAddrType,
        tBgpPeerNgAddr,
        tBgpRouteInvalidReason,
        tBgpRouteNLRI,
        tBgpASN4Byte
    }
    STATUS      current
    DESCRIPTION
        "[CAUSE] The tBgp4RouteInvalid notification is generated when the
         received route is invalid for a specific reason and the route can not
         be used or advertised further.

         [EFFECT] The BGP peer ignores the route and flags the path attribute
         and the route so that the peer/tribe that was attempting to advertise
         the associated route can skip this route. The BGP peering is not torn
         down in this case.

         [RECOVERY] There is no recovery required for this notification."
    ::= { tBgpNotifications 15 }

tBgp4PathAttrInvalid             NOTIFICATION-TYPE
    OBJECTS     {
        vRtrID,
        tBgpPeerNgAddrType,
        tBgpPeerNgAddr,
        tBgp4PathAttrType,
        tBgp4PathAttrLength,
        tBgp4PathAttribute,
        tBgpASN4Byte
    }
    STATUS      current
    DESCRIPTION
        "[CAUSE] The tBgp4PathAttrInvalid notification is generated when an
         error with a path attribute tBgp4PathAttribute is detected.

         [EFFECT] A log entry is generated for each withdrawn route. Further
         effect depends on fault-tolerance and graceful-restart settings.

         [RECOVERY] There is no recovery required for this notification."
    ::= { tBgpNotifications 16 }

tBgp4WithdrawnRtFromUpdateError  NOTIFICATION-TYPE
    OBJECTS     {
        vRtrID,
        tBgpPeerNgAddrType,
        tBgpPeerNgAddr,
        tBgp4WithdrawnRoutePrefix,
        tBgpASN4Byte
    }
    STATUS      current
    DESCRIPTION
        "[CAUSE] The tBgp4WithdrawnRtFromUpdateError notification is generated
         when NLRI is withdrawn because of error in BGP update message.

         [EFFECT] This notification has no direct effect. The withdrawn routes
         are logged to aid debugging and tracking back the root cause of the
         problem.

         [RECOVERY] There is no recovery required for this notification."
    ::= { tBgpNotifications 17 }

tBgp4UpdateInvalid               NOTIFICATION-TYPE
    OBJECTS     {
        vRtrID,
        tBgpPeerNgAddrType,
        tBgpPeerNgAddr,
        tBgp4UpdateMessage,
        tBgpASN4Byte
    }
    STATUS      current
    DESCRIPTION
        "[CAUSE] The tBgp4UpdateInvalid notification is generated when an
         UPDATE message has a critical length error or an error not specific to
         any path attribute.

         [EFFECT] A log entry is generated for each withdrawn route. Further
         effect depends on fault-tolerance and graceful-restart settings.

         [RECOVERY] There is no recovery required for this notification."
    ::= { tBgpNotifications 18 }

tBgpReceivedInvalidNlri          NOTIFICATION-TYPE
    OBJECTS     {
        tBgp4BadErrorMessage,
        tBgp4BadErrorMessageType
    }
    STATUS      current
    DESCRIPTION
        "[CAUSE] The tBgpReceivedInvalidNlri notification is generated when
         there is a parsing error in BGP routes in update messages that is not
         related to attribute errors. Fault tolerance is not applicable here.

         [EFFECT] BGP will send a notification message to the peer and bring
         down the peering.

         [RECOVERY] Peering will be re-established with the offending peer."
    ::= { tBgpNotifications 19 }

tBgpMaxNgPfxLmt                  NOTIFICATION-TYPE
    OBJECTS     {
        tBgpPeerNgPfxLmtMaxPrefix,
        tBgpASN4Byte
    }
    STATUS      current
    DESCRIPTION
        "[CAUSE] A tBgpMaxNgPfxLmt notification is generated when the number of
         routes learned from the peer has exceeded the configured maximum.

         [EFFECT] No direct effect but if the peer continues to advertise more
         routes then the number of routes may exceed the configured maximum
         (tBgpPeerNgPfxLmtMaxPrefix). In that case the peer would just be
         disabled.

         [RECOVERY] Increase the max-prefix for this peer."
    ::= { tBgpNotifications 20 }

tBgpMaxNgPfxLmtThresholdReached  NOTIFICATION-TYPE
    OBJECTS     {
        tBgpPeerNgPfxLmtMaxPrefix,
        tBgpPeerNgPfxLmtThreshold,
        tBgpASN4Byte
    }
    STATUS      current
    DESCRIPTION
        "[CAUSE] A tBgpMaxNgPfxLmtThresholdReached notification is generated
         when the number of routes learned from the peer has exceeded
         tBgpPeerNgPfxLmtThreshold percent of the configured maximum
         (tBgpPeerNgPfxLmtMaxPrefix).

         [EFFECT] No direct effect but if the peer continues to advertise more
         routes then the number of routes may exceed the configured maximum
         (tBgpPeerNgPfxLmtMaxPrefix). In that case the peer would just be
         disabled.

         [RECOVERY] Increase the max-prefix for this peer."
    ::= { tBgpNotifications 21 }

tBgpInstanceDynamicPeerLmtReachd NOTIFICATION-TYPE
    OBJECTS     {
        tBgpInstanceDynamicPeerLimit,
        tBgpASN4Byte
    }
    STATUS      current
    DESCRIPTION
        "[CAUSE] A tBgpInstanceDynamicPeerLmtReachd notification is generated
         when the dynamic peer limit for this BGP instance is reached.

         [EFFECT] Whenever an incoming connection for a new dynamic session
         would cause dynamic peer limit for this BGP instance to be exceeded,
         the connection attempt is rejected.

         [RECOVERY] Increase the dynamic peer limit for this BGP instance."
    ::= { tBgpNotifications 22 }

tBgpPGDynamicPeerLmtReached      NOTIFICATION-TYPE
    OBJECTS     {
        tBgpPGDynamicPeerLimit,
        tBgpASN4Byte
    }
    STATUS      current
    DESCRIPTION
        "[CAUSE] A tBgpPGDynamicPeerLmtReached notification is generated when
         the dynamic peer limit for this group is reached.

         [EFFECT] Whenever an incoming connection for a new dynamic session
         would cause dynamic peer limit for this group to be exceeded, the
         connection attempt is rejected.

         [RECOVERY] Increase the dynamic peer limit for this group."
    ::= { tBgpNotifications 23 }

tBgp4PathAttrDiscarded           NOTIFICATION-TYPE
    OBJECTS     {
        vRtrID,
        tBgpPeerNgAddrType,
        tBgpPeerNgAddr,
        tBgp4PathAttrType,
        tBgp4PathAttrLength,
        tBgp4PathAttribute,
        tBgpASN4Byte
    }
    STATUS      current
    DESCRIPTION
        "[CAUSE] The tBgp4PathAttrDiscarded notification is generated when a
         path attribute tBgp4PathAttribute is discarded from an UPDATE message.
         A path attribute may be discarded because it is malformed.

         [EFFECT] A log entry is generated for each path attribute discarded
         from an UPDATE message. The UPDATE message continues to be processed.

         [RECOVERY] There is no recovery required for this notification."
    ::= { tBgpNotifications 24 }

tBgpInstConvStateTransition      NOTIFICATION-TYPE
    OBJECTS     {
        tBgpConvergenceState,
        tBgpConvergenceFamily,
        tBgpOldConvergenceState
    }
    STATUS      current
    DESCRIPTION
        "[CAUSE] The tBgpInstConvStateTransition notification is  generated
         when the convergence state for IPv4-unicast transitions from partial
         to converged.

         [EFFECT] A log entry is generated.

         [RECOVERY] There is no recovery required for this notification."
    ::= { tBgpNotifications 25 }

tBgpPGDynNbrIfMaxSessLmtReachd   NOTIFICATION-TYPE
    OBJECTS     {
        tBgpPGDynNbrIfMaxSessions
    }
    STATUS      current
    DESCRIPTION
        "[CAUSE] The tBgpPGDynNbrIfMaxSessLmtReachd notification is generated
         when the dynamic session limit for this interface is reached.

         [EFFECT] Whenever an incoming connection for a new dynamic session
         would cause dynamic session limit for this interface to be exceeded,
         the connection attempt is rejected.

         [RECOVERY] Increase the dynamic peer limit for this interface."
    ::= { tBgpNotifications 26 }

END
