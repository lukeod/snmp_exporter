TIMETRA-TC-MIB DEFINITIONS ::= BEGIN

IMPORTS
    InetAddress, InetAddressIPv6,
    InetAddressPrefixLength, InetAddressType
                                                         FROM INET-ADDRESS-MIB
    Integer32, IpAddress, MODULE-IDENTITY,
    Unsigned32
                                                         FROM SNMPv2-SMI
    DisplayString, TEXTUAL-CONVENTION,
    TruthValue
                                                         FROM SNMPv2-TC
    timetraModules
                                                         FROM TIMETRA-GLOBAL-MIB
    ;

timetraTCMIBModule               MODULE-IDENTITY
    LAST-UPDATED "201701010000Z"
    ORGANIZATION "Nokia"
    CONTACT-INFO
        "Nokia SROS Support
         Web: http://www.nokia.com"
    DESCRIPTION
        "This document is the SNMP MIB module for the SNMP Textual Conventions
         (TCs) used in the Nokia SROS manageability instrumentation.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201701010000Z"
    DESCRIPTION
        "Rev 15.0               1 Jan 2017 00:00
         15.0 release of the TIMETRA-TC-MIB."

    REVISION    "201601010000Z"
    DESCRIPTION
        "Rev 14.0               1 Jan 2016 00:00
         14.0 release of the TIMETRA-TC-MIB."

    REVISION    "201501010000Z"
    DESCRIPTION
        "Rev 13.0               1 Jan 2015 00:00
         13.0 release of the TIMETRA-TC-MIB."

    REVISION    "201401010000Z"
    DESCRIPTION
        "Rev 12.0               1 Jan 2014 00:00
         12.0 release of the TIMETRA-TC-MIB."

    REVISION    "201102010000Z"
    DESCRIPTION
        "Rev 9.0                1 Feb 2011 00:00
         9.0 release of the TIMETRA-TC-MIB."

    REVISION    "200902280000Z"
    DESCRIPTION
        "Rev 7.0                28 Feb 2009 00:00
         7.0 release of the TIMETRA-TC-MIB."

    REVISION    "200807010000Z"
    DESCRIPTION
        "Rev 6.1                01 Jul 2008 00:00
         6.1 release of the TIMETRA-TC-MIB."

    REVISION    "200801010000Z"
    DESCRIPTION
        "Rev 6.0                01 Jan 2008 00:00
         6.0 release of the TIMETRA-TC-MIB."

    REVISION    "200701010000Z"
    DESCRIPTION
        "Rev 5.0                01 Jan 2007 00:00
         5.0 release of the TIMETRA-TC-MIB."

    REVISION    "200603230000Z"
    DESCRIPTION
        "Rev 4.0                23 Mar 2006 00:00
         4.0 release of the TIMETRA-TC-MIB."

    REVISION    "200508310000Z"
    DESCRIPTION
        "Rev 3.0                31 Aug 2005 00:00
         3.0 release of the TIMETRA-TC-MIB."

    REVISION    "200501240000Z"
    DESCRIPTION
        "Rev 2.1                24 Jan 2005 00:00
         2.1 release of the TIMETRA-TC-MIB."

    REVISION    "200401150000Z"
    DESCRIPTION
        "Rev 2.0                15 Jan 2004 00:00
         2.0 release of the TIMETRA-TC-MIB."

    REVISION    "200308150000Z"
    DESCRIPTION
        "Rev 1.2                15 Aug 2003 00:00
         1.2 release of the TIMETRA-TC-MIB."

    REVISION    "200301200000Z"
    DESCRIPTION
        "Rev 1.0                20 Jan 2003 00:00
         1.0 Release of the TIMETRA-TC-MIB."

    REVISION    "200105290000Z"
    DESCRIPTION
        "Rev 0.1                14 Aug 2000 00:00
         First version of the TIMETRA-TC-MIB."

    ::= { timetraModules 2 }

TmnxFPNumber                     ::= TEXTUAL-CONVENTION
    STATUS      current
    DESCRIPTION
        "The unique value that identifies the forwarding plane within a
         specific IOM card in the system."
    SYNTAX      Unsigned32 (1..12)

TmnxFPNumberOrZero               ::= TEXTUAL-CONVENTION
    STATUS      current
    DESCRIPTION
        "The unique value that identifies the forwarding plane within a
         specific IOM card in the system.

         Value 0 means this value is not applicable."
    SYNTAX      Unsigned32 (0 | 1..12)

InterfaceIndex                   ::= TEXTUAL-CONVENTION
    DISPLAY-HINT "d"
    STATUS      current
    DESCRIPTION
        "A unique value, greater than zero, for each interface
         or interface sub-layer in the managed system.  It is
         recommended that values are assigned contiguously
         starting from 1.  The value for each interface sub-
         layer must remain constant at least from one re-
         initialization of the entity's network management
         system to the next re-initialization."
    SYNTAX      Integer32

TmnxPortID                       ::= TEXTUAL-CONVENTION
    STATUS      current
    DESCRIPTION
        "A portid is a unique 32 bit number with special encoding.

         Refer to TIMETRA-CHASSIS-MIB::tmnxChassisPortIdScheme for a
         description of the various port mapping schemes used by the system for
         physical ports and channels.

         An 'invalid portid' is a TmnxPortID with a value of 0x1e000000."
    SYNTAX      Unsigned32

TmnxEncapVal                     ::= TEXTUAL-CONVENTION
    STATUS      current
    DESCRIPTION
        "The value of the label used to identify the entity using the specified
         encapsulation value on a specific port.

         The format of this object depends on the encapsulation type defined on
         this port.

         When the encapsulation is nullEncap the value of this object must be
         zero.

         31                                   0
         +--------+--------+--------+--------+
         |00000000 00000000 00000000 00000000|
         +--------+--------+--------+--------+

         When the encapsulation is dot1qEncap the value of this object is equal
         to the 12-bit IEEE 802.1Q VLAN ID.

         31                                   0
         +--------+--------+--------+--------+
         |00000000 00000000 0000XXXX XXXXXXXX|
         +--------+--------+--------+--------+

         Bit 31 is set to 0 in the case of tagged-VLAN.
         Bit 31 is set to 1 in the case of dotq-CP as follows:
         31                                   0
         +--------+--------+--------+--------+
         |10000000 00000000 0000XXXX XXXXXXXX|
         +--------+--------+--------+--------+

         When the encapsulation is mplsEncap the value of this object is equal
         to the 20-bit LSP ID.

         31                                   0
         +--------+--------+--------+--------+
         |00000000 0000XXXX XXXXXXXX XXXXXXXX|
         +--------+--------+--------+--------+

         When the encapsulation is qinqEncap, the value of the outer 802.1Q
         VLAN ID is encoded in the least significant 16 bits, and the value of
         the inner VLAN ID is encoded in the most significant 16 bits.

         31   inner             outer       0
         +--------+--------+--------+--------+
         |0000YYYY YYYYYYYY 0000XXXX XXXXXXXX|
         +--------+--------+--------+--------+

         where:
             - '*' is represented as 4095.
             - '0' is represented as 0.
             - any other value in between as a valid tag.
             - '*.null' is represented in the following way:

               31                                  0
               +--------+--------+--------+--------+
               |10000000 00000000 00001111 11111111|
               +--------+--------+--------+--------+

             - 'null.null' is represented in the following way:

               31                                  0
               +--------+--------+--------+--------+
               |10000000 00000000 00010000 00000000|
               +--------+--------+--------+--------+



         Bit 30 is set to 0 in the case of tagged-qinq for the bottom tag. Bit
         30 is set to 1 in the case of qinq-CP with bottom tag. Bit 15 is set
         to 0 in the case of tagged-qinq for the top tag. Bit 15 is set to 1 in
         the case of qinq-CP with top tag.

         Example of qinq encoding for CP.* saps:

         31                                   0
         +--------+--------+--------+--------+
         |00001111 11111111 1000XXXX XXXXXXXX|
         +--------+--------+--------+--------+


         Example of qinq encoding for X.CP saps:

         31                                   0
         +--------+--------+--------+--------+
         |0100XXXX XXXXXXXX 0000XXXX XXXXXXXX|
         +--------+--------+--------+--------+

         Some ports have a restrictions to the encapsulation types that they
         can support and hence impose restrictions on the respective formats
         defined above."
    SYNTAX      Unsigned32

QTag                             ::= TEXTUAL-CONVENTION
    STATUS      current
    DESCRIPTION
        "The QTag data type is a 12-bit integer tag used to identify
         a service.  The values 0 and 4095 are not allowed."
    SYNTAX      Integer32 (1..4094)

QTagOrNone                       ::= TEXTUAL-CONVENTION
    STATUS      current
    DESCRIPTION
        "The QTag data type is a 12-bit integer tag used to identify
         a service.  The values 0 and 4095 are not allowed.

         The value '-1' indicates the absence of a VLAN tag."
    SYNTAX      Integer32 (-1 | 1..4094)

QTagOrZero                       ::= TEXTUAL-CONVENTION
    STATUS      current
    DESCRIPTION
        "The data type QTagOrZero represents a VLAN tag.

         The value '0' indicates that no VLAN tag is provisioned, or that its
         value is unknown."
    SYNTAX      Unsigned32 (0..4094)

QTagFullRange                    ::= TEXTUAL-CONVENTION
    STATUS      current
    DESCRIPTION
        "The data type QTagFullRange represents a VLAN tag. A VLAN tag is 12
         bits is size. The data type QTagFullRange covers the whole range of
         possible values. (0..4095 or 0x0 .. 0xFFF)"
    SYNTAX      Unsigned32 (0..4095)

QTagFullRangeOrNone              ::= TEXTUAL-CONVENTION
    STATUS      current
    DESCRIPTION
        "The data type QTagFullRangeOrNone represents a VLAN tag. A VLAN tag is
         12 bits is size. The data type QTagFullRange covers the whole range of
         possible values. (0..4095 or 0x0 .. 0xFFF).

         The value '-1' indicates the absence of a VLAN tag."
    SYNTAX      Integer32 (-1 | 0..4095)

TmnxSapAASubScope                ::= TEXTUAL-CONVENTION
    STATUS      current
    DESCRIPTION
        "The TmnxSapAASubScope data type is an enumerated integer
         that specifies the scope of the AA subscriber.
         Values:
           none       (0) - The AA subscriber has no scope.
           subscriber (1) - The AA subscriber has esm subscriber scope.
           mac        (2) - The AA subscriber has esm MAC host scope."
    SYNTAX      INTEGER {
        none       (0),
        subscriber (1),
        mac        (2)
    }

TmnxStrSapId                     ::= TEXTUAL-CONVENTION
    STATUS      current
    DESCRIPTION
        "The value of TmnxStrSapId is a printable string which contains the
         owner SAP Id or equivalent on a remote system.

         The string should contain the printable string equivalent of the
         textual conventions TmnxPortID and TmnxEncapVal in the format
         specified as TmnxPortID[:TmnxEncapVal]"
    SYNTAX      DisplayString (SIZE (0..32))

IpAddressPrefixLength            ::= TEXTUAL-CONVENTION
    STATUS      current
    DESCRIPTION
        "the number of bits to match in an IP address mask."
    SYNTAX      Integer32 (0..32)

TmnxActionType                   ::= TEXTUAL-CONVENTION
    STATUS      current
    DESCRIPTION
        "The TmnxActionType data type is an enumerated integer
         that describes the values used to support action or
         operation style commands.  Setting a variable of this
         type to 'doAction' causes the action to occur.  GETs and
         GETNEXTs on this variable return 'not-applicable'."
    SYNTAX      INTEGER {
        doAction      (1),
        notApplicable (2)
    }

TmnxAdminState                   ::= TEXTUAL-CONVENTION
    STATUS      current
    DESCRIPTION
        "The TmnxAdminState data type is an enumerated integer that describes
         the values used to identify the administratively desired state of
         functional modules."
    SYNTAX      INTEGER {
        noop         (1),
        inService    (2),
        outOfService (3)
    }

TmnxOperState                    ::= TEXTUAL-CONVENTION
    STATUS      current
    DESCRIPTION
        "The TmnxOperState data type is an enumerated integer that describes
         the values used to identify the current operational state of
         functional modules."
    SYNTAX      INTEGER {
        unknown      (1),
        inService    (2),
        outOfService (3),
        transition   (4)
    }

TmnxStatus                       ::= TEXTUAL-CONVENTION
    STATUS      current
    DESCRIPTION
        "The TmnxStatus data type is an enumerated integer that describes the
         values used to identify the current status of functional modules in the
         system such as OSPF and MPLS protocols. Setting this variable to
         'create' causes instantiation of the feature in the system.  Setting it
         to 'delete' removes the instance and all associated configuration
         information."
    SYNTAX      INTEGER {
        create (1),
        delete (2)
    }

TmnxEnabledDisabledAdminState    ::= TEXTUAL-CONVENTION
    STATUS      current
    DESCRIPTION
        "The TmnxEnabledDisabledAdminState data type is an enumerated integer
         that describes the values used to identify whether an entity is
         'enabled' or 'disabled'. It is to be used for admin state leafs."
    SYNTAX      INTEGER {
        enabled  (1),
        disabled (2)
    }

TmnxEnabledDisabled              ::= TEXTUAL-CONVENTION
    STATUS      current
    DESCRIPTION
        "The TmnxEnabledDisabled data type is an enumerated integer that
         describes the values used to identify whether an entity is 'enabled'
         or 'disabled'."
    SYNTAX      INTEGER {
        enabled  (1),
        disabled (2)
    }

TmnxEnabledDisabledOrNA          ::= TEXTUAL-CONVENTION
    STATUS      current
    DESCRIPTION
        "An object of type TmnxEnabledDisabledOrNA indicates if an entity is
         enabled or disabled, or if enabled/disabled is not applicable to the
         entity."
    SYNTAX      INTEGER {
        enabled       (1),
        disabled      (2),
        notApplicable (3)
    }

TmnxEnabledDisabledOrInherit     ::= TEXTUAL-CONVENTION
    STATUS      current
    DESCRIPTION
        "The TmnxEnabledDisabledOrInherit data type is an enumerated integer
         that describes the values used to identify whether an entity is
         'enabled', 'disabled' or inherits its state from another object that
         is usually in another MIB table."
    SYNTAX      INTEGER {
        enabled  (1),
        disabled (2),
        inherit  (3)
    }

TmnxPermitDeny                   ::= TEXTUAL-CONVENTION
    STATUS      current
    DESCRIPTION
        "The TmnxPermitDeny data type is an enumerated integer that describes
         whether the entity its action is permitted or denied."
    SYNTAX      INTEGER {
        deny   (2),
        permit (3)
    }

TmnxPermitDenyOrInherit          ::= TEXTUAL-CONVENTION
    STATUS      current
    DESCRIPTION
        "The TmnxPermitDenyOrInherit data type is an enumerated integer that
         describes whether an entity its action is permitted or denied.

         Value 'inherit' indicates the state is inherited from another object
         that is usually in another MIB table."
    SYNTAX      INTEGER {
        inherit (1),
        deny    (2),
        permit  (3)
    }

TmnxTimeInterval                 ::= TEXTUAL-CONVENTION
    STATUS      current
    DESCRIPTION
        "The TmnxTimeInterval data type is used anywhere the SNMPv2-TC
         TimeInterval TEXTUAL-CONVENTION can be used when an object requires
         longer intervals than 248 days.

         A period of time, measured in units of centiseconds."
    SYNTAX      Unsigned32

TNamedItem                       ::= TEXTUAL-CONVENTION
    STATUS      current
    DESCRIPTION
        "The name of an item.  When used as an index to a table, the item
         name uniquely identifies the instance.  When used in a reference
         (TNamedItemOrEmpty) the item name entry must exist in the table.

         Note, use only NVT ASCII displayable characters here, no control
         characters, no UTF-8, etc."
    SYNTAX      DisplayString (SIZE (1..32))

TNamedItemOrEmpty                ::= TEXTUAL-CONVENTION
    STATUS      current
    DESCRIPTION
        "The name of an item, or an empty string.  When used in a reference
         (TNamedItemOrEmpty) the item name entry must exist in the table.

         Note, use only NVT ASCII displayable characters here, no control
         characters, no UTF-8, etc."
    SYNTAX      DisplayString (SIZE (0|1..32))

TLNamedItem                      ::= TEXTUAL-CONVENTION
    STATUS      current
    DESCRIPTION
        "The long name of an item.  When used as an index to a table, the item
         name uniquely identifies the instance.  When used in a reference
         (TLNamedItemOrEmpty) the item name entry must exist in the table.

         Note, use only NVT ASCII displayable characters here, no control
         characters, no UTF-8, etc."
    SYNTAX      DisplayString (SIZE (1..64))

TLNamedItemOrEmpty               ::= TEXTUAL-CONVENTION
    STATUS      current
    DESCRIPTION
        "The long name of an item, or an empty string.  When used in a reference
         (TLNamedItemOrEmpty) the item name entry must exist in the table.

         Note, use only NVT ASCII displayable characters here, no control
         characters, no UTF-8, etc."
    SYNTAX      DisplayString (SIZE (0|1..64))

TXLNamedItem                     ::= TEXTUAL-CONVENTION
    STATUS      current
    DESCRIPTION
        "The extra long name of an item.  When used as an index to a table,
         the item name uniquely identifies the instance. When used in a
         reference (TXLNamedItemOrEmpty) the item name entry must
         exist in the table.

         Note, use only NVT ASCII displayable characters here, no control
         characters, no UTF-8, etc."
    SYNTAX      DisplayString (SIZE (1..255))

TXLNamedItemOrEmpty              ::= TEXTUAL-CONVENTION
    STATUS      current
    DESCRIPTION
        "The extra long name of an item, or an empty string.  When used in a
         reference (TXLNamedItemOrEmpty) the item name entry must exist in
         the table.

         Note, use only NVT ASCII displayable characters here, no control
         characters, no UTF-8, etc."
    SYNTAX      DisplayString (SIZE (0|1..255))

TItemDescription                 ::= TEXTUAL-CONVENTION
    STATUS      current
    DESCRIPTION
        "Description for an item.  Note, use only NVT ASCII displayable characters
         here, no control characters, no UTF-8, etc."
    SYNTAX      DisplayString (SIZE (0..80))

TItemLongDescription             ::= TEXTUAL-CONVENTION
    STATUS      current
    DESCRIPTION
        "Longer description for an item.  Note, use only NVT ASCII displayable
         characters here, no control characters, no UTF-8, etc."
    SYNTAX      DisplayString

TItemVeryLongDescription         ::= TEXTUAL-CONVENTION
    STATUS      current
    DESCRIPTION
        "Longer description for an item.  Note, use only NVT ASCII displayable
         characters here, no control characters, no UTF-8, etc."
    SYNTAX      DisplayString (SIZE (0..255))

TRegularExpression               ::= TEXTUAL-CONVENTION
    STATUS      current
    DESCRIPTION
        "A regular expression string."
    SYNTAX      DisplayString

TmnxHttpRedirectUrl              ::= TEXTUAL-CONVENTION
    STATUS      current
    DESCRIPTION
        "A string that represents an HTTP URL configured for HTTP redirection.

         The string may contain a macro '$URL' that specifies substitution of
         '$URL' by another string; the origin of that string is documented
         where this textual convention is used.

         The string may contain a macro '$MAC' that specifies substitution of
         '$MAC' by another string, representing a MAC address; the origin of
         that string is documented where this textual convention is used.

         The string may contain a macro '$IP' that specifies substitution of
         '$IP' by another string, representing an IP address; the origin of
         that string is documented where this textual convention is used.

         The string may contain a macro '$SUB' that specifies substitution of
         '$SUB' by another string, representing an subscriber ID; the origin of
         that string is documented where this textual convention is used.

         The string may contain a macro '$SAP' that specifies substitution of
         '$SAP' by another string, representing a SAP (Service Access Point);
         the origin of that string is documented where this textual convention
         is used.

         The string may contain a macro '$SAPDESC' that specifies substitution
         of '$SAPDESC' by another string; the origin of that string is
         documented where this textual convention is used.

         The string may contain a macro '$CID' that specifies substitution of
         '$CID' by a bytestring, representing a circuit-id or interface-id; the
         origin of that string is documented where this textual convention is
         used.

         The string may contain a macro '$RID' that specifies substitution of
         '$RID' by a bytestring, representing a remote-id; the origin of that
         string is documented where this textual convention is used.

         Not all substitution macro's are supported in every situation; an
         unsupported macro is ignored (substituted with nothing); the set of
         supported macro's should be documented where this textual convention
         is used."
    SYNTAX      DisplayString

TmnxBofDisplayStringURL          ::= TEXTUAL-CONVENTION
    STATUS      current
    DESCRIPTION
        "A string that represents an URL in the BOF. If the URL contains login
         information in the form of 'username:password' this login information
         will be blanked out in the SNMP get response, by replacing the login
         information with '*:*'."
    SYNTAX      DisplayString (SIZE (0..199))

TmnxDisplayStringURL             ::= TEXTUAL-CONVENTION
    STATUS      current
    DESCRIPTION
        "A string that represents an URL. If the URL contains login information
         in the form of 'username:password' this login information will be
         blanked out in the SNMP get response, by replacing the login
         information with '*:*'."
    SYNTAX      DisplayString (SIZE (0..180))

TmnxVRtrID                       ::= TEXTUAL-CONVENTION
    STATUS      current
    DESCRIPTION
        "A number used to identify a virtual router instance in the system."
    SYNTAX      Integer32 (1..10240)

TmnxVRtrIDOrZero                 ::= TEXTUAL-CONVENTION
    STATUS      current
    DESCRIPTION
        "A number used to identify a virtual router instance in the system. The
         number 0 will have special significance in the context the TC is used."
    SYNTAX      Integer32 (0..10240)

VRtrIgmpHostMcRDstStatType       ::= TEXTUAL-CONVENTION
    STATUS      current
    DESCRIPTION
        "The VRtrIgmpHostMcRDstStatType data type is an enumerated integer that
         indicates a type of IGMP host mcast reporting destination statistics."
    SYNTAX      INTEGER {
        joinTx       (1),
        joinDenyTx   (2),
        dropTx       (3),
        joinLost     (4),
        joinDenyLost (5),
        dropLost     (6)
    }

TmnxBgpAutonomousSystem          ::= TEXTUAL-CONVENTION
    STATUS      current
    DESCRIPTION
        "an autonomous system (AS) number."
    REFERENCE
        "BGP4-MIB.bgpPeerRemoteAs"
    SYNTAX      Integer32 (0..65535)

TmnxBgpLocalPreference           ::= TEXTUAL-CONVENTION
    STATUS      current
    DESCRIPTION
        "a local route preference value."
    REFERENCE
        "RFC 1771 section 4.3 Path Attributes e)"
    SYNTAX      Unsigned32

TmnxBgpPreference                ::= TEXTUAL-CONVENTION
    STATUS      current
    DESCRIPTION
        "a route preference value."
    REFERENCE
        "RFC 1771 section 4.3 Path Attributes e)"
    SYNTAX      Unsigned32 (0..255)

TmnxCustId                       ::= TEXTUAL-CONVENTION
    STATUS      current
    DESCRIPTION
        "A number used to identify a Customer or Subscriber. This ID must be
         unique within the Service Domain. The value 0 is used as the null ID."
    SYNTAX      Unsigned32 (0 | 1..2147483647)

TmnxCustIdNoZero                 ::= TEXTUAL-CONVENTION
    STATUS      current
    DESCRIPTION
        "A number used to identify a Customer or Subscriber. This ID must be
         unique within the Service Domain."
    SYNTAX      Unsigned32 (1..2147483647)

BgpPeeringStatus                 ::= TEXTUAL-CONVENTION
    STATUS      current
    DESCRIPTION
        "The status of the BGP peering session."
    SYNTAX      INTEGER {
        notApplicable       (0),
        installed           (1),
        notInstalled        (2),
        noEnhancedSubmgt    (3),
        wrongAntiSpoof      (4),
        parentItfDown       (5),
        hostInactive        (6),
        noDualHomingSupport (7),
        invalidRadiusAttr   (8),
        noDynamicPeerGroup  (9),
        duplicatePeer       (10),
        maxPeersReached     (11),
        l2AwNotSupported    (12),
        gtpNotSupported     (13),
        genError            (14)
    }

TmnxRipListenerStatus            ::= TEXTUAL-CONVENTION
    STATUS      current
    DESCRIPTION
        "The status of the RIP Listener session."
    SYNTAX      INTEGER {
        notApplicable    (0),
        active           (1),
        inactive         (2),
        noEnhancedSubmgt (3),
        wrongAntiSpoof   (4),
        parentItfDown    (5),
        hostInactive     (6),
        l2AwNotSupported (7),
        gtpNotSupported  (8),
        mcStandby        (9),
        ripDisabled      (10)
    }

TmnxServId                       ::= TEXTUAL-CONVENTION
    STATUS      current
    DESCRIPTION
        "A number used to identify a Service. This ID must be unique within the
         Service Domain. The value 0 is used as the null ID."
    SYNTAX      Unsigned32 (0 | 1..2147483647 | 2147483648 | 2147483649 | 2147483650 | 2147483651..2147483690 | 2147483691..2148007980 | 2148007981..2148012076 | 2148012077..2148016172 | 2148016173..2148278316 | 2148278317 | 2148278318..2148278381 | 2148278382 | 2148278382..2148278386 | 2148278387..2148282482)

TmnxExtServId                    ::= TEXTUAL-CONVENTION
    STATUS      current
    DESCRIPTION
        "A number used to identify an external Service. This ID must be unique
         within the Service Domain. The value 0 is used as the null ID."
    SYNTAX      Unsigned32 (0 | 1..2147483647)

TmnxAdminStateUpDown             ::= TEXTUAL-CONVENTION
    STATUS      current
    DESCRIPTION
        "TmnxAdminStateUpDown data type is an enumerated integer that describes
         the values used to identify the administrative state of a snmp row."
    SYNTAX      INTEGER {
        up   (1),
        down (2)
    }

TmnxAdminStateTruthValue         ::= TEXTUAL-CONVENTION
    STATUS      current
    DESCRIPTION
        "TmnxAdminStateTruthValue data type is an TruthValue object used to
         identify the administrative state of a snmp row.

         A value of 'true' means the snmp row is administrative 'up'."
    SYNTAX      TruthValue

TruthValueNoTypeTranslator       ::= TEXTUAL-CONVENTION
    STATUS      current
    DESCRIPTION
        "Represents a boolean value."
    SYNTAX      INTEGER {
        true  (1),
        false (2)
    }

ServiceAdminStatus               ::= TEXTUAL-CONVENTION
    STATUS      current
    DESCRIPTION
        "ServiceAdminStatus data type is an enumerated integer that describes
         the values used to identify the administrative state of a service."
    SYNTAX      INTEGER {
        up   (1),
        down (2)
    }

ServiceOperStatus                ::= TEXTUAL-CONVENTION
    STATUS      current
    DESCRIPTION
        "ServiceOperStatus data type is an enumerated integer that describes
         the values used to identify the current operational state of a
         service."
    SYNTAX      INTEGER {
        up   (1),
        down (2)
    }

TPolicyID                        ::= TEXTUAL-CONVENTION
    STATUS      current
    DESCRIPTION
        "The identification number of a policy."
    SYNTAX      Unsigned32 (0..65535 | 65536 | 65537 | 65538 | 65539 | 65540)

TTmplPolicyID                    ::= TEXTUAL-CONVENTION
    STATUS      current
    DESCRIPTION
        "The identification number of a policy for template objects."
    SYNTAX      Unsigned32 (0..65535)

TQosIngressPolicyID              ::= TEXTUAL-CONVENTION
    STATUS      current
    DESCRIPTION
        "The identification number of a QoS ingress policy."
    SYNTAX      TPolicyID

TSapIngressPolicyID              ::= TEXTUAL-CONVENTION
    STATUS      current
    DESCRIPTION
        "The identification number of a SAP ingress policy."
    SYNTAX      TPolicyID

TSapEgressPolicyID               ::= TEXTUAL-CONVENTION
    STATUS      current
    DESCRIPTION
        "The identification number of a SAP egress policy."
    SYNTAX      TPolicyID (1..65535 | 65536 | 65537 | 65538 | 65539)

TAnyQosPolicyID                  ::= TEXTUAL-CONVENTION
    STATUS      current
    DESCRIPTION
        "The identification number of QoS policy. Any value greater than 65535
         indicates the policy was created by the system.

         The format is:
            +--------------------------------+
            |<----C-----><-B><------A------->|
            +--------------------------------+
            31                               0

         where:
          A (16 bits) is the base policy identifier.
          B (4 bits) is the 'policy type'.
          C (12 bits) is the auxiliary identifier.

         When policy type = 0 (0000b), the acceptable range for base policy
                                      identifier is 1..65535. This is the user
                                      configured values.
         When policy type = 1 (0001b)  [NAT/LNS], the acceptable range for base
                                      policy identifier is 0..4. These policies
                                      are considered 'internal' and cannot be
                                      created or modified by the user.
         When policy type = 2 (0010b)  The auxiliary identifier represents
                                      internal policies that are created
                                      by the system based on dynamic flow based
                                      requests from diameter and cannot be
                                      modified by the user. These polices
                                      ranges from 1..2047. For all other policy
                                      types, the auxiliary identifier must be
                                      zero."
    SYNTAX      Unsigned32 (1..4294967295)

TAnyQosPolicyIDorZero            ::= TEXTUAL-CONVENTION
    STATUS      current
    DESCRIPTION
        "The identification number of QoS policy. Refer to the description of
         the textual convention TAnyQosPolicyID for more info on how this
         number is to be interpreted."
    SYNTAX      Unsigned32 (0 | 1..4294967295)

TSdpIngressPolicyID              ::= TEXTUAL-CONVENTION
    STATUS      current
    DESCRIPTION
        "The identification number of a SDP ingress network policy."
    SYNTAX      TPolicyID

TSdpEgressPolicyID               ::= TEXTUAL-CONVENTION
    STATUS      current
    DESCRIPTION
        "The identification number of a SDP egress network policy."
    SYNTAX      TPolicyID

TQosQGrpInstanceIDorZero         ::= TEXTUAL-CONVENTION
    STATUS      current
    DESCRIPTION
        "The identification number of a QoS queue group instance.

         The value of '0' indicates the system determined default value."
    SYNTAX      Unsigned32 (0 | 1..65535)

TmnxCreateOrigin                 ::= TEXTUAL-CONVENTION
    STATUS      current
    DESCRIPTION
        "The TmnxCreateOrigin indicates the entity that created the entry."
    SYNTAX      INTEGER {
        manual         (1),
        bgp-l2vpn      (2),
        radius         (3),
        bgpSignalL2vpn (4),
        multiSegmentPW (5),
        vplsPmsi       (6),
        dynScript      (7),
        bof            (8),
        bgpSignalVpws  (9),
        evpn           (13),
        satellites     (15),
        fpe            (16),
        evpnIsa        (17),
        greBridged     (18),
        tli            (19),
        pdn            (20),
        ipsec          (23),
        esa            (24),
        pfcpCups       (25),
        manual-mci     (26)
    }

TmnxBsxTransitIpPolicyId         ::= TEXTUAL-CONVENTION
    STATUS      current
    DESCRIPTION
        "TmnxBsxTransitIpPolicyId identifies a transit IP policy."
    SYNTAX      Unsigned32 (1..65535)

TmnxBsxTransitIpPolicyIdOrZero   ::= TEXTUAL-CONVENTION
    STATUS      current
    DESCRIPTION
        "TmnxBsxTransitIpPolicyId identifies a transit ip policy.

         The value '0' indicates an invalid transit IP policy."
    SYNTAX      Unsigned32 (0 | 1..65535)

TmnxBsxTransPrefPolicyId         ::= TEXTUAL-CONVENTION
    STATUS      current
    DESCRIPTION
        "TmnxBsxTransPrefPolicyId identifies a transit prefix policy."
    SYNTAX      Unsigned32 (1..65535)

TmnxBsxTransPrefPolicyIdOrZero   ::= TEXTUAL-CONVENTION
    STATUS      current
    DESCRIPTION
        "TmnxBsxTransPrefPolicyId identifies a transit prefix policy.

         The value '0' indicates an invalid transit prefix policy."
    SYNTAX      Unsigned32 (0 | 1..65535)

TmnxBsxAarpId                    ::= TEXTUAL-CONVENTION
    STATUS      current
    DESCRIPTION
        "TmnxBsxAarpId identifies an instance of the AA Redundancy Protocol
         (AARP)."
    SYNTAX      Unsigned32 (1..65535)

TmnxBsxAarpIdOrZero              ::= TEXTUAL-CONVENTION
    STATUS      current
    DESCRIPTION
        "TmnxBsxAarpIdOrZero identifies an instance of the AA Redundancy
         Protocol (AARP).

         The value of '0' indicates an invalid AARP instance."
    SYNTAX      Unsigned32 (0 | 1..65535)

TmnxBsxAarpServiceRefType        ::= TEXTUAL-CONVENTION
    STATUS      current
    DESCRIPTION
        "TmnxBsxAarpServiceRefType identifies the role of the SAP or Spoke SDP
         service point being referenced by an AARP instance. This reference is
         made in the context of a AARP instance identified by
         TmnxBsxAarpIdOrZero.

         The service reference types are:

         none(0)                - service reference type is not applicable.

         dualHomed(1)           - the service reference point is a SAP or
                                  Spoke SDP connected into a dually homed
                                  network being protected by the AARP instance.

         shuntSubscriberSide(2) - the service reference point is a Spoke SDP
                                  acting as a subscriber side shunt used by
                                  the AARP instance. A subscriber side shunt
                                  carries the local from/to subscriber
                                  traffic when AA is performed remotely.

         shuntNetworkSide(3)    - the service reference point is a Spoke SDP
                                  acting as a network side shunt used by
                                  the AARP instance. A network side shunt
                                  carries the local from/to network
                                  traffic when AA is performed remotely.

         dualHomedSecondary(4)  - the secondary service reference point is a
                                  SAP or Spoke SDP connected into a dually
                                  homed network being protected by the AARP
                                  instance. It functions as a backup to the
                                  'dualHomed(1)' primary reference point.

         For the case when TmnxBsxAarpIdOrZero refers to the invalid AARP
         instance '0', the service reference type is 'none(0)'."
    SYNTAX      INTEGER {
        none                (0),
        dualHomed           (1),
        shuntSubscriberSide (2),
        shuntNetworkSide    (3),
        dualHomedSecondary  (4)
    }

TmnxBsxIsaAaGroupIndexOrZero     ::= TEXTUAL-CONVENTION
    STATUS      current
    DESCRIPTION
        "TmnxBsxIsaAaGroupIndexOrZero is an index of a group of BSX MDAs. The
         value of zero indicates that no BSX MDA group is specified."
    SYNTAX      Unsigned32 (0..255)

TmnxBsxAaGrpPartIndexOrZero      ::= TEXTUAL-CONVENTION
    STATUS      current
    DESCRIPTION
        "TmnxBsxAaGrpPartIndexOrZero is an index of an Application Assurance
         partition within an Application Assurance group, and is a unique
         32-bit number encoded as follows.

         | 32   25 | 24    9 | 8      1 |
         +---------+---------+----------+
         |    0    | partidx |  groupidx|  Partition Index
         +---------+---------+----------+

         - groupidx represents a group of ISA MDAs and has
          a valid range from 1..255. The corresponding
          TIMETRA-BSX-NG-MIB::tmnxBsxIsaAaGroupIndex must
          already exist in the tmnxBsxIsaAaGrpTable.

         - partidx represents a partition within a group and
          has a valid range from 0..65535. A partition index
          of '0' represents group wide information.

         The value of zero indicates that no Application Assurance partition is
         specified"
    SYNTAX      Unsigned32 (0..16777215)

TmnxBsxAaSubHttpUrlParam         ::= TEXTUAL-CONVENTION
    STATUS      current
    DESCRIPTION
        "Optional text string used to customize the URL used for Application
         Assurance HTTP In-Browser Notification and automatically appended at
         the end of the notification script URL as an argument."
    SYNTAX      DisplayString (SIZE (0..247))

TSapEgrEncapGrpQosPolicyIdOrZero ::= TEXTUAL-CONVENTION
    STATUS      current
    DESCRIPTION
        "TSapEgrEncapGrpQosPolicyIdOrZero identifies SAP egress Encapsulation
         group QoS policy.

         The value '0' indicates no QoS policy is set."
    SYNTAX      Unsigned32 (0 | 1..65535)

TSapEgrEncapGroupType            ::= TEXTUAL-CONVENTION
    STATUS      current
    DESCRIPTION
        "TSapEgrEncapGroupType identifies Encapsulation group type on SAP
         egress."
    SYNTAX      INTEGER {
        isid (1)
    }

TSapEgrEncapGroupActionType      ::= TEXTUAL-CONVENTION
    STATUS      current
    DESCRIPTION
        "TSapEgrEncapGroupActionType identifies Encapsulation group action type
         on SAP egress. It is used to create or destroy row entries in an
         associated table."
    SYNTAX      INTEGER {
        create  (1),
        destroy (2)
    }

TPerPacketOffset                 ::= TEXTUAL-CONVENTION
    STATUS      current
    DESCRIPTION
        "The value, in bytes, of the adjustment to make to the size of each
         packet for accounting."
    SYNTAX      Integer32 (-32..31)

TPerPacketOffsetOvr              ::= TEXTUAL-CONVENTION
    STATUS      current
    DESCRIPTION
        "The value, in bytes, of the override of the adjustment to make to the
         size of each packet for accounting. A value of -128 indicates no
         override."
    SYNTAX      Integer32 (-128 | -32..31)

TIngressHsmdaPerPacketOffset     ::= TEXTUAL-CONVENTION
    STATUS      current
    DESCRIPTION
        "The value, in bytes, of the adjustment to make to the size of each
         incoming packet for accounting."
    SYNTAX      Integer32 (-32..31)

TIngHsmdaPerPacketOffsetOvr      ::= TEXTUAL-CONVENTION
    STATUS      current
    DESCRIPTION
        "The value, in bytes, of the override of the adjustment to make to the
         size of each incoming packet for accounting. A value of -128 indicates
         no override."
    SYNTAX      Integer32 (-128 | -32..31)

TEgressQPerPacketOffset          ::= TEXTUAL-CONVENTION
    STATUS      current
    DESCRIPTION
        "The value, in bytes, of the adjustment to make to the size of each
         packet for accounting."
    SYNTAX      Integer32 (-64..32)

TEgressPerPacketOffset           ::= TEXTUAL-CONVENTION
    STATUS      current
    DESCRIPTION
        "The value, in bytes, of the adjustment to make to the size of each
         packet for accounting."
    SYNTAX      Integer32 (-64..31)

TEgressPerPacketOffsetOvr        ::= TEXTUAL-CONVENTION
    STATUS      current
    DESCRIPTION
        "The value, in bytes, of the override for the adjustment to make to the
         size of each packet for accounting. A value of -128 indicates no
         override."
    SYNTAX      Integer32 (-128 | -64..31)

TEgressHsmdaPerPacketOffset      ::= TEXTUAL-CONVENTION
    STATUS      current
    DESCRIPTION
        "The value, in bytes, of the adjustment to make to the size of each
         outgoing packet for accounting."
    SYNTAX      Integer32 (-64..31)

TEgrHsmdaPerPacketOffsetOvr      ::= TEXTUAL-CONVENTION
    STATUS      current
    DESCRIPTION
        "The value, in bytes, of the override of the adjustment to make to the
         size of each outgoing packet for accounting. A value of -128 indicates
         no override."
    SYNTAX      Integer32 (-128 | -64..31)

TEgressQMaxDataTrans             ::= TEXTUAL-CONVENTION
    STATUS      current
    DESCRIPTION
        "The value, in bytes, transmitted at every scheduling opportunity for
         the queues."
    SYNTAX      Integer32 (-1 | 512..32768)

TIngressQPerPacketOffset         ::= TEXTUAL-CONVENTION
    STATUS      current
    DESCRIPTION
        "The value, in bytes, of the adjustment to make to the size of each
         incoming packet for accounting.

         Only even values are supported."
    SYNTAX      Integer32 (-32..30)

THsmdaCounterIdOrZero            ::= TEXTUAL-CONVENTION
    STATUS      current
    DESCRIPTION
        "The identification number of a HSMDA  counter.
         The value 0 indicates an undefined counter id."
    SYNTAX      Unsigned32 (0 | 1..8)

THsmdaCounterIdOrZeroOrAll       ::= TEXTUAL-CONVENTION
    STATUS      current
    DESCRIPTION
        "The identification number of a HSMDA  counter.
         The value (0) indicates an undefined counter id.
         The value (-1) is used to indicate all counters."
    SYNTAX      Integer32 (-1 | 0 | 1..8)

TIngressHsmdaCounterId           ::= TEXTUAL-CONVENTION
    STATUS      current
    DESCRIPTION
        "The identification number of a HSMDA ingress counter."
    SYNTAX      Unsigned32 (1..8)

TIngressHsmdaCounterIdOrZero     ::= TEXTUAL-CONVENTION
    STATUS      current
    DESCRIPTION
        "The identification number of a HSMDA ingress counter. The value 0
         indicates an undefined counter id."
    SYNTAX      Unsigned32 (0 | 1..8)

TEgressHsmdaCounterId            ::= TEXTUAL-CONVENTION
    STATUS      current
    DESCRIPTION
        "The identification number of a HSMDA egress counter."
    SYNTAX      Unsigned32 (1..8)

TEgressHsmdaCounterIdOrZero      ::= TEXTUAL-CONVENTION
    STATUS      current
    DESCRIPTION
        "The identification number of a HSMDA egress counter. The value 0
         indicates an undefined counter id."
    SYNTAX      Unsigned32 (0 | 1..8)

TEgrRateModType                  ::= TEXTUAL-CONVENTION
    STATUS      current
    DESCRIPTION
        "The data type TEgrRateModType represents the type of egress-rate
         modification that is to be applied."
    SYNTAX      INTEGER {
        none           (1),
        aggRateLimit   (2),
        namedScheduler (3)
    }

TPolicyStatementName             ::= TEXTUAL-CONVENTION
    STATUS      current
    DESCRIPTION
        "The name of a policy statement, when used as index in a table."
    SYNTAX      TNamedItem

TPolicyStatementNameOrEmpty      ::= TEXTUAL-CONVENTION
    STATUS      current
    DESCRIPTION
        "The name of a policy statement, when an object refers to it."
    SYNTAX      TNamedItemOrEmpty

TLPolicyStatementNameOrEmpty     ::= TEXTUAL-CONVENTION
    STATUS      current
    DESCRIPTION
        "The long name of a policy statement, when an object refers to it."
    SYNTAX      TLNamedItemOrEmpty

TLPolicyNameOrExpOrEmpty         ::= TEXTUAL-CONVENTION
    STATUS      current
    DESCRIPTION
        "The long name of a policy statement or an expression or an empty
         string.

         A logical expression contains terms and operators and can contain
         sub-expressions enclosed in round brackets.

         A term is a string of type TPolicyStatementName.

         An operator can be the string 'AND', 'OR', and 'NOT'."
    SYNTAX      TLNamedItemOrEmpty

TXLPolicyNameOrExpOrEmpty        ::= TEXTUAL-CONVENTION
    STATUS      current
    DESCRIPTION
        "The extra long name of a policy statement or an expression or an empty
         string.

         A logical expression contains terms and operators and can contain
         sub-expressions enclosed in round brackets.

         A term is a string of type TPolicyStatementName.

         An operator can be the string 'AND', 'OR', and 'NOT'."
    SYNTAX      TXLNamedItemOrEmpty

TmnxVcType                       ::= TEXTUAL-CONVENTION
    STATUS      current
    DESCRIPTION
        "The value of TmnxVcType is an enumerated integer that indicates a
         Virtual Circuit (VC) type. 'frDlciMartini(1)' replaces the old
         'frDlci' when used over martini tunnels."
    SYNTAX      INTEGER {
        frDlciMartini (1),
        atmSdu        (2),
        atmCell       (3),
        ethernetVlan  (4),
        ethernet      (5),
        atmVccCell    (9),
        atmVpcCell    (10),
        ipipe         (11),
        satopE1       (17),
        satopT1       (18),
        satopE3       (19),
        satopT3       (20),
        cesopsn       (21),
        cesopsnCas    (23),
        frDlci        (25),
        mirrorDest    (4096)
    }

TmnxVcId                         ::= TEXTUAL-CONVENTION
    STATUS      current
    DESCRIPTION
        "A 32 bit number is used to identify a VC(Virtual Circuit). The VC ID
         cannot be 0."
    SYNTAX      Unsigned32 (1..4294967295)

TmnxVcIdOrNone                   ::= TEXTUAL-CONVENTION
    STATUS      current
    DESCRIPTION
        "A 32 bit number is used to identify a VC(Virtual Circuit). A value of
         0 indicates no VC ID is configured or available."
    SYNTAX      Unsigned32 (0 | 1..4294967295)

DateAndTimeOrEmpty               ::= TEXTUAL-CONVENTION
    STATUS      current
    DESCRIPTION
        "An object of type DateAndTimeOrEmpty data type contains a date-time
         specification as in SNMPv2-TC::DateAndTime, or is empty"
    SYNTAX      OCTET STRING (SIZE (0 | 8 | 11))

ClassIndex                       ::= TEXTUAL-CONVENTION
    STATUS      current
    DESCRIPTION
        "Source/Destination class index."
    SYNTAX      Unsigned32 (1..255)

ClassIndexOrNone                 ::= TEXTUAL-CONVENTION
    STATUS      current
    DESCRIPTION
        "Source/Destination class index or none(0)."
    SYNTAX      Unsigned32 (0 | 1..255)

Dot1PPriority                    ::= TEXTUAL-CONVENTION
    STATUS      current
    DESCRIPTION
        "IEEE 802.1p priority.  zero is lowest, seven is highest.
         -1 means not set"
    SYNTAX      Integer32 (-1 | 0..7)

Dot1PPriorityMask                ::= TEXTUAL-CONVENTION
    STATUS      current
    DESCRIPTION
        "IEEE 802.1p priority mask.  zero is lowest, seven is highest."
    SYNTAX      Integer32 (0..7)

Dot1PPriorityNonZeroMask         ::= TEXTUAL-CONVENTION
    STATUS      current
    DESCRIPTION
        "IEEE 802.1p priority mask."
    SYNTAX      Integer32 (1..7)

ServiceAccessPoint               ::= TEXTUAL-CONVENTION
    STATUS      current
    DESCRIPTION
        "802.2 LLC SAP value, Source and Destination."
    REFERENCE
        "assigned numbers:  http://www.iana.org/assignments/ieee-802-numbers"
    SYNTAX      Integer32 (-1 | 0..255)

TLspExpValue                     ::= TEXTUAL-CONVENTION
    STATUS      current
    DESCRIPTION
        "MPLS Experimental bits. -1 means not set."
    SYNTAX      Integer32 (-1 | 0..7)

TIpProtocol                      ::= TEXTUAL-CONVENTION
    STATUS      current
    DESCRIPTION
        "IP protocol number. Well known protocol numbers include ICMP(1),
         TCP(6), UDP(17).

         -1 means value not set.
         -2 indicates protocol wildcard for UDP and TCP."
    REFERENCE
        "http://www.iana.org/assignments/protocol-numbers"
    SYNTAX      Integer32 (-2 | -1 | 0..255)

TIpProtocolNumber                ::= TEXTUAL-CONVENTION
    STATUS      current
    DESCRIPTION
        "IP protocol number.

         Well known protocol numbers include ICMP(1), TCP(6), UDP(17)."
    REFERENCE
        "http://www.iana.org/assignments/protocol-numbers"
    SYNTAX      Integer32 (0..255)

TIpOption                        ::= TEXTUAL-CONVENTION
    STATUS      current
    DESCRIPTION
        "IP packet options octet.  explanation of the octet bits:

         IP OPTION NUMBERS

         The Internet Protocol (IP) has provision for optional header fields
         identified by an option type field.  Options 0 and 1 are exactly one
         octet which is their type field.  All other options have their one
         octet type field, followed by a one octet length field, followed by
         length-2 octets of option data.  The option type field is subdivided
         into a one bit copied flag, a two bit class field, and a five bit
         option number.  These taken together form an eight bit value for the
         option type field.  IP options are commonly referred to by this value.


         Copy Class Number Value Name                Reference
         ---- ----- ------ ----- ------------------------------- ---------
            0     0      0     0 EOOL   - End of Options List    [RFC791,JBP]
            0     0      1     1 NOP    - No Operation           [RFC791,JBP]
            1     0      2   130 SEC    - Security                  [RFC1108]
            1     0      3   131 LSR    - Loose Source Route     [RFC791,JBP]
            0     2      4    68 TS     - Time Stamp             [RFC791,JBP]
            1     0      5   133 E-SEC  - Extended Security         [RFC1108]
            1     0      6   134 CIPSO  - Commercial Security           [???]
            0     0      7     7 RR     - Record Route           [RFC791,JBP]
            1     0      8   136 SID    - Stream ID              [RFC791,JBP]
            1     0      9   137 SSR    - Strict Source Route    [RFC791,JBP]
            0     0     10    10 ZSU    - Experimental Measurement      [ZSu]
            0     0     11    11 MTUP   - MTU Probe                 [RFC1191]*
            0     0     12    12 MTUR   - MTU Reply                 [RFC1191]*
            1     2     13   205 FINN   - Experimental Flow Control    [Finn]
            1     0     14   142 VISA   - Experimental Access Control [Estrin]
            0     0     15    15 ENCODE - ???                      [VerSteeg]
            1     0     16   144 IMITD  - IMI Traffic Descriptor        [Lee]
            1     0     17   145 EIP    - Extended Internet Protocol[RFC1385]
            0     2     18    82 TR     - Traceroute        [RFC1393]
            1     0     19   147 ADDEXT - Address Extension    [Ullmann IPv7]
            1     0     20   148 RTRALT - Router Alert              [RFC2113]
            1     0     21   149 SDB    - Selective Directed Broadcast[Graff]
            1     0     22   150 NSAPA  - NSAP Addresses          [Carpenter]
            1     0     23   151 DPS    - Dynamic Packet State        [Malis]
            1     0     24   152 UMP    - Upstream Multicast Pkt. [Farinacci]

         [Note, an asterisk (*) denotes an obsoleted IP Option Number.]
            "
    REFERENCE
        "http://www.iana.org/assignments/ip-parameters"
    SYNTAX      Integer32 (0..255)

TIcmpTypeOrNone                  ::= TEXTUAL-CONVENTION
    STATUS      current
    DESCRIPTION
        "ICMP type.

         The value -1 means ICMP type is not set."
    REFERENCE
        "www.iana.org/assignments/icmp-parameters/icmp-parameters.xhtml#icmp-parameters-types"
    SYNTAX      Integer32 (-1 | 0..255)

TIcmpCodeOrNone                  ::= TEXTUAL-CONVENTION
    STATUS      current
    DESCRIPTION
        "ICMP code.

         The value -1 means ICMP code is not set."
    REFERENCE
        "www.iana.org/assignments/icmp-parameters/icmp-parameters.xhtml#icmp-parameters-codes"
    SYNTAX      Integer32 (-1 | 0..255)

TTcpUdpPort                      ::= TEXTUAL-CONVENTION
    STATUS      current
    DESCRIPTION
        "The number of a TCP or UDP port. Well known port numbers include
         ftp-data(20), ftp(21), telnet(23), smtp(25), http(80), pop3(110),
         nntp(119), snmp(161), snmptrap(162), etc."
    REFERENCE
        "http://www.iana.org/assignments/port-numbers"
    SYNTAX      Integer32 (0 | 1..65535)

TOperator                        ::= TEXTUAL-CONVENTION
    STATUS      current
    DESCRIPTION
        "The operator specifies the manner in which a couple of other MIB
         objects in the table are supposed to be used.

         Operator        Value1               Value2
         ----------------------------------------------------
         none(0)         Any(0)               Any(0)
         eq(1)           Specified Value      Any(0)
         range(2)        Starting Value       Ending Value
         lt(3)           Specified Value      Any(0)
         gt(4)           Specified Value      Any(0)

         'Any(0)' specifies that, this object can accept any values
          but would default to 0. "
    SYNTAX      INTEGER {
        none  (0),
        eq    (1),
        range (2),
        lt    (3),
        gt    (4)
    }

TTcpUdpPortOperator              ::= TEXTUAL-CONVENTION
    STATUS      current
    DESCRIPTION
        "The operator used for checking on TCP/UDP ports values and ranges"
    SYNTAX      TOperator

TFrameType                       ::= TEXTUAL-CONVENTION
    STATUS      current
    DESCRIPTION
        "The type of the frame for which this mac filter match criteria is
         defined."
    SYNTAX      INTEGER {
        e802dot3     (0),
        e802dot2LLC  (1),
        e802dot2SNAP (2),
        ethernetII   (3)
    }

TQueueId                         ::= TEXTUAL-CONVENTION
    STATUS      current
    DESCRIPTION
        "The value of TQueueId specifies the identification number of a
         queue.  A value of zero (0) indicates that no specific queue
         identification has been assigned for this object. When an object
         of type TQueueId is an SNMP table index, an index value of zero
         (0) is not allowed and a noCreation error will be returned."
    SYNTAX      Integer32 (0 | 1..32)

TQueueIdOrAll                    ::= TEXTUAL-CONVENTION
    STATUS      current
    DESCRIPTION
        "The value of TQueueIdOrAll specifies the identification number of a
         queue

         A value of zero (0) indicates that no specific queue identification
         has been assigned for this object.

         A value of (-1) indicates 'all queues'."
    SYNTAX      Integer32 (-1 | 0 | 1..32)

TIngressQueueId                  ::= TEXTUAL-CONVENTION
    STATUS      current
    DESCRIPTION
        "The value of TIngressQueueId specifies the identification number
         of an ingress queue.  A value of zero (0) indicates that no
         specific queue identification has been assigned for this object.
         When an object of type TIngressQueueId is an SNMP table index,
         an index value of zero (0) is not allowed and a noCreation error
         will be returned."
    SYNTAX      Integer32 (0 | 1..32)

TEgressQueueId                   ::= TEXTUAL-CONVENTION
    STATUS      current
    DESCRIPTION
        "The value of TEgressQueueId specifies the identification number
         of an egress queue.  A value of zero (0) indicates that no
         specific queue identification has been assigned for this object.
         When an object of type TEgressQueueId is an SNMP table index,
         an index value of zero (0) is not allowed and a noCreation error
         will be returned."
    SYNTAX      Integer32 (0 | 1..8)

TIngressHsmdaQueueId             ::= TEXTUAL-CONVENTION
    STATUS      current
    DESCRIPTION
        "The value of TIngressHsmdaQueueId specifies the identification number
         of a HSMDA ingress queue.  A value of zero (0) indicates that no
         specific queue identification has been assigned for this object.
         When an object of type TIngressHsmdaQueueId is an SNMP table index,
         an index value of zero (0) is not allowed and a noCreation error
         will be returned."
    SYNTAX      Integer32 (0 | 1..8)

TEgressHsmdaQueueId              ::= TEXTUAL-CONVENTION
    STATUS      current
    DESCRIPTION
        "The value of TEgressHsmdaQueueId specifies the identification number
         of a HSMDA egress queue.  A value of zero (0) indicates that no
         specific queue identification has been assigned for this object.
         When an object of type TEgressHsmdaQueueId is an SNMP table index,
         an index value of zero (0) is not allowed and a noCreation error
         will be returned."
    SYNTAX      Integer32 (0 | 1..8)

THsmdaSchedulerPolicyGroupId     ::= TEXTUAL-CONVENTION
    STATUS      current
    DESCRIPTION
        "The value of THsmdaSchedulerPolicyGroupId specifies the identification
         number of a HSMDA scheduler policy group.  A value of zero (0)
         indicates that no specific group identification has been assigned for
         this object. When an object of type THsmdaSchedulerPolicyGroupId is
         an SNMP table index, an index value of zero (0) is not allowed and a
         noCreation error will be returned."
    SYNTAX      Integer32 (0 | 1..2)

THsmdaPolicyIncludeQueues        ::= TEXTUAL-CONVENTION
    STATUS      current
    DESCRIPTION
        "The value of THsmdaPolicyIncludeQueues specifies which queues are to
         be scheduled in the same class in a HSMDA scheduler."
    SYNTAX      INTEGER {
        q1to2 (1),
        q1to3 (2)
    }

THsmdaPolicyScheduleClass        ::= TEXTUAL-CONVENTION
    STATUS      current
    DESCRIPTION
        "The value of THsmdaPolicyScheduleClass the class at which the queues
         specified by THsmdaPolicyIncludeQueues in a HSMDA scheduler."
    SYNTAX      Integer32 (1..3)

TDSCPName                        ::= TEXTUAL-CONVENTION
    STATUS      current
    DESCRIPTION
        "The name of a Differential Services Code Point value."
    SYNTAX      TNamedItem

TDSCPNameOrEmpty                 ::= TEXTUAL-CONVENTION
    STATUS      current
    DESCRIPTION
        "The name of a Differential Services Code Point value."
    SYNTAX      TNamedItemOrEmpty

TDSCPValue                       ::= TEXTUAL-CONVENTION
    STATUS      current
    DESCRIPTION
        "The value of a Differential Services Code Point."
    SYNTAX      Integer32 (0..63)

TDSCPValueOrNone                 ::= TEXTUAL-CONVENTION
    STATUS      current
    DESCRIPTION
        "The value of a Differential Services Code Point (DSCP). A value of -1
         means that no DSCP value is configured or available."
    SYNTAX      Integer32 (-1 | 0..63)

TDSCPFilterActionValue           ::= TEXTUAL-CONVENTION
    STATUS      current
    DESCRIPTION
        "The value of a Differential Services Code Point. -1 means not set."
    SYNTAX      Integer32 (-1 | 0..255)

TFCName                          ::= TEXTUAL-CONVENTION
    STATUS      current
    DESCRIPTION
        "The name of a Forwarding Class entry."
    SYNTAX      TNamedItem

TFCNameOrEmpty                   ::= TEXTUAL-CONVENTION
    STATUS      current
    DESCRIPTION
        "The name of a Forwarding Class entry."
    SYNTAX      TNamedItemOrEmpty

TFCSet                           ::= TEXTUAL-CONVENTION
    STATUS      current
    DESCRIPTION
        "This data type describes a set of Forwarding Classes."
    SYNTAX      BITS {
        be (0),
        l2 (1),
        af (2),
        l1 (3),
        h2 (4),
        ef (5),
        h1 (6),
        nc (7)
    }

TFCType                          ::= TEXTUAL-CONVENTION
    STATUS      current
    DESCRIPTION
        "This data type enumerates the Forwarding Classes."
    SYNTAX      INTEGER {
        be (0),
        l2 (1),
        af (2),
        l1 (3),
        h2 (4),
        ef (5),
        h1 (6),
        nc (7)
    }

TFCTypeOrNone                    ::= TEXTUAL-CONVENTION
    STATUS      current
    DESCRIPTION
        "This data type enumerates the Forwarding Classes."
    SYNTAX      INTEGER {
        none (-1),
        be   (0),
        l2   (1),
        af   (2),
        l1   (3),
        h2   (4),
        ef   (5),
        h1   (6),
        nc   (7)
    }

TmnxTunnelType                   ::= TEXTUAL-CONVENTION
    STATUS      current
    DESCRIPTION
        "The type of this tunnel entity."
    SYNTAX      INTEGER {
        sdp     (1),
        ldp     (2),
        rsvp    (3),
        gre     (4),
        bypass  (5),
        invalid (6),
        bgp     (7)
    }

TmnxTunnelID                     ::= TEXTUAL-CONVENTION
    STATUS      current
    DESCRIPTION
        "The identifying value for a BGP-VPRN tunnel.  Depending on the
         tunnel type the associated tunnel id may be an sdp-id, an LSP ID
         or zero(0)."
    SYNTAX      Unsigned32

TmnxBgpRouteTarget               ::= TEXTUAL-CONVENTION
    STATUS      current
    DESCRIPTION
        "TmnxBgpRouteTarget is an readable string that specifies the extended
         community name to be accepted by a Route Reflector Server or
         advertised by the router when reflecting any routes. I.e, it does not
         apply to routes that are not reflected by the router."
    SYNTAX      OCTET STRING (SIZE (1..32))

TmnxVPNRouteDistinguisher        ::= TEXTUAL-CONVENTION
    STATUS      current
    DESCRIPTION
        "The VPRN route distinguisher is a 8-octet object. It contains a
         2-octet type field followed by a 6-octet value field. The type field
         specify how to interpret the value field.

         Type 0 specifies two subfields as a 2-octet administrative field and a
         4-octet assigned number subfield.

         Type 1 specifies two subfields as a 4-octet administrative field which
         must contain an IP address and a 2-octet assigned number subfield.

         Type 2 specifies two subfields as a 4-octet administrative field which
         contains a 4-octet AS number and a 2-octet assigned number subfield."
    SYNTAX      OCTET STRING (SIZE (8))

SdpBindId                        ::= TEXTUAL-CONVENTION
    STATUS      current
    DESCRIPTION
        "The value used to uniquely identify an SDP Binding. The first four
         octets correspond to the zero-extended 16-bit SDP ID, while the
         remaining four octets correspond to the 32-bit VC ID, both encoded in
         network byte order."
    SYNTAX      OCTET STRING (SIZE (8))

TmnxVRtrMplsLspID                ::= TEXTUAL-CONVENTION
    STATUS      current
    DESCRIPTION
        "A unique value for each Label Switched Path in the managed system.

         The higher range IDs are used for segment routing LSPs.

         The lower range IDs are used for regular LSPs."
    SYNTAX      Unsigned32 (0..65535 | 65536..131070)

TmnxVRtrMplsLspIDNoZero          ::= TEXTUAL-CONVENTION
    STATUS      current
    DESCRIPTION
        "A unique value, greater than zero, for each Label Switched Path in the
         managed system.

         The higher range IDs are used for segment routing LSPs.

         The lower range IDs are used for regular LSPs."
    SYNTAX      Unsigned32 (1..65535 | 65536..131070)

TPortSchedulerPIR                ::= TEXTUAL-CONVENTION
    STATUS      current
    DESCRIPTION
        "The Peak Information Rate (PIR) rate to be used in kbps. The value -1
         means maximum rate."
    SYNTAX      Integer32 (-1 | 1..100000000)

TPortSchedulerAggRateLimitPIR    ::= TEXTUAL-CONVENTION
    STATUS      current
    DESCRIPTION
        "The Peak Information Rate (PIR) rate to be used in kbps. The value -1
         means maximum rate."
    SYNTAX      Integer32 (-1 | 1..800000000)

TPortSchedulerPIRRate            ::= TEXTUAL-CONVENTION
    STATUS      current
    DESCRIPTION
        "The Peak Information Rate (PIR) rate to be used in kbps. The value -1
         means maximum rate."
    SYNTAX      Integer32 (-1 | 1..800000000)

TPortSchedulerCIR                ::= TEXTUAL-CONVENTION
    STATUS      current
    DESCRIPTION
        "The Committed Information Rate (CIR) rate to be used in kbps. The
         value -1 means maximum rate."
    SYNTAX      Integer32 (-1 | 0..800000000)

TPortQosPIRRate                  ::= TEXTUAL-CONVENTION
    STATUS      current
    DESCRIPTION
        "The Peak Information Rate (PIR) rate to be used in kbps."
    SYNTAX      Unsigned32 (1..10000)

TPortQosCIRRate                  ::= TEXTUAL-CONVENTION
    STATUS      current
    DESCRIPTION
        "The Committed Information Rate (CIR) rate to be used in kbps."
    SYNTAX      Unsigned32 (0..10000)

TWeight                          ::= TEXTUAL-CONVENTION
    STATUS      current
    DESCRIPTION
        "The weight of the specified entity while feeding into the parent."
    SYNTAX      Integer32 (0..100)

TWeightOverride                  ::= TEXTUAL-CONVENTION
    STATUS      current
    DESCRIPTION
        "The weight of the specified entity while feeding into the parent. A
         value of -2 specifies no override."
    SYNTAX      Integer32 (-2 | 0..100)

TNonZeroWeight                   ::= TEXTUAL-CONVENTION
    STATUS      current
    DESCRIPTION
        "The weight of the specified entity while feeding into the parent."
    SYNTAX      Integer32 (1..100)

TPolicerWeight                   ::= TEXTUAL-CONVENTION
    STATUS      current
    DESCRIPTION
        "The relative weight of the specified entity while feeding into the
         parent."
    SYNTAX      Integer32 (1..100)

THsWrrWeightOvr                  ::= TEXTUAL-CONVENTION
    STATUS      current
    DESCRIPTION
        "The THsWrrWeightOvr data type specifies the override weight of the
         corresponding HS queue feeding into its parent WRR scheduler. A value
         of -2 specifies no override."
    SYNTAX      Integer32 (-2 | 1..127)

THsClassWeightOverride           ::= TEXTUAL-CONVENTION
    STATUS      current
    DESCRIPTION
        "The THsClassWeightOverride data type specifies the weight of the
         corresponding HS class feeding into its parent shaper. A value of -2
         specifies no override."
    SYNTAX      Integer32 (-2 | 1 | 2 | 4 | 8)

THsmdaWeight                     ::= TEXTUAL-CONVENTION
    STATUS      current
    DESCRIPTION
        "The weight of the specified HSMDA entity while feeding into the
         parent."
    SYNTAX      Integer32 (1..100)

THsmdaWrrWeight                  ::= TEXTUAL-CONVENTION
    STATUS      current
    DESCRIPTION
        "The weight of the specified HSMDA entity while feeding into the
         parent."
    SYNTAX      Integer32 (1..32)

THsmdaWeightClass                ::= TEXTUAL-CONVENTION
    STATUS      current
    DESCRIPTION
        "The weight of the specified HSMDA entity while feeding into the
         parent."
    SYNTAX      INTEGER {
        class1 (1),
        class2 (2),
        class4 (4),
        class8 (8)
    }

THsmdaWeightOverride             ::= TEXTUAL-CONVENTION
    STATUS      current
    DESCRIPTION
        "The weight of the specified HSMDA entity while feeding into the
         parent. A value of -2 specifies no override."
    SYNTAX      Integer32 (-2 | 1..100)

THsmdaWrrWeightOverride          ::= TEXTUAL-CONVENTION
    STATUS      current
    DESCRIPTION
        "The weight of the specified HSMDA entity while feeding into the
         parent. A value of -2 specifies no override."
    SYNTAX      Integer32 (-2 | 1..32)

TCIRRate                         ::= TEXTUAL-CONVENTION
    STATUS      current
    DESCRIPTION
        "The CIR rate to be used in kbps. The value -1 means maximum rate."
    SYNTAX      Integer32 (-1 | 0..100000000)

THPolCIRRate                     ::= TEXTUAL-CONVENTION
    STATUS      current
    DESCRIPTION
        "The CIR rate to be used in kbps. The value -1 means maximum rate."
    SYNTAX      Integer32 (-1 | 0..2000000000)

TRateType                        ::= TEXTUAL-CONVENTION
    STATUS      current
    DESCRIPTION
        "The type of the PIR/CIR rate. The value 'kbps' means the rate is
         specified in kbps. The value 'percent' means the rate is specified in
         percentage"
    SYNTAX      INTEGER {
        kbps    (1),
        percent (2)
    }

TBWRateType                      ::= TEXTUAL-CONVENTION
    STATUS      current
    DESCRIPTION
        "The type of the PIR/CIR percent rate. The value 'kbps' means the rate
         is specified in kbps. The value 'percentPortLimit' means the rate is
         specified in percentage of port limit. The value 'percentLocalLimit'
         means the rate is specified in percentage of local limit."
    SYNTAX      INTEGER {
        kbps              (1),
        percentPortLimit  (2),
        percentLocalLimit (3)
    }

TPSPRateType                     ::= TEXTUAL-CONVENTION
    STATUS      current
    DESCRIPTION
        "The type of the PIR/CIR rate being applied to port scheduler policy.
         The value of 'kbps' means the rate is specified in kbps. The value of
         'percentActivePortLimit' means the rate is specified in percentage of
         active port bandwidth, that is, bandwidth of active ports in a LAG."
    SYNTAX      INTEGER {
        kbps             (1),
        percentLocal     (2),
        percentLagActive (3)
    }

TPolicerRateType                 ::= TEXTUAL-CONVENTION
    STATUS      current
    DESCRIPTION
        "The type of the PIR/CIR percent rate. The value 'kbps' means the rate
         is specified in kbps. The value 'percentLocalLimit' means the rate is
         specified in percentage of local limit."
    SYNTAX      INTEGER {
        kbps              (1),
        percentLocalLimit (2)
    }

TCIRRateOverride                 ::= TEXTUAL-CONVENTION
    STATUS      current
    DESCRIPTION
        "The CIR rate to be used in kbps. The value -1 means maximum rate. A
         value of -2 specifies no override."
    SYNTAX      Integer32 (-2 | -1 | 0..100000000)

THPolCIRRateOverride             ::= TEXTUAL-CONVENTION
    STATUS      current
    DESCRIPTION
        "The CIR rate to be used in kbps. The value -1 means maximum rate. A
         value of -2 specifies no override."
    SYNTAX      Integer32 (-2 | -1 | 0..2000000000)

TCIRPercentOverride              ::= TEXTUAL-CONVENTION
    STATUS      current
    DESCRIPTION
        "The CIR percentage rate specified in centipercent. A value of -2
         specifies no override."
    SYNTAX      Integer32 (-2 | 0..10000)

THsmdaCIRKRate                   ::= TEXTUAL-CONVENTION
    STATUS      current
    DESCRIPTION
        "The HSMDA CIR rate to be used in Kbps. The value -1 means maximum
         rate."
    SYNTAX      Integer32 (-1 | 0..100000000)

THsmdaCIRKRateOverride           ::= TEXTUAL-CONVENTION
    STATUS      current
    DESCRIPTION
        "The HSMDA CIR rate to be used in Kbps. The value -1 means maximum
         rate. A value of -2 specifies no override."
    SYNTAX      Integer32 (-2 | -1 | 0..100000000)

THsmdaCIRMRate                   ::= TEXTUAL-CONVENTION
    STATUS      current
    DESCRIPTION
        "The HSMDA CIR rate to be used in Mbps. The value -1 means maximum
         rate."
    SYNTAX      Integer32 (-1 | 0..100000)

THsmdaCIRMRateOverride           ::= TEXTUAL-CONVENTION
    STATUS      current
    DESCRIPTION
        "The HSMDA CIR rate to be used in Mbps. The value -1 means maximum
         rate. A value of -2 specifies no override."
    SYNTAX      Integer32 (-2 | -1 | 0..100000)

TPIRRate                         ::= TEXTUAL-CONVENTION
    STATUS      current
    DESCRIPTION
        "The PIR rate to be used in kbps. The value -1 means maximum rate."
    SYNTAX      Integer32 (-1 | 1..100000000)

THPolVirtualSchePIRRate          ::= TEXTUAL-CONVENTION
    STATUS      current
    DESCRIPTION
        "The PIR rate to be used in kbps. The value -1 means maximum rate."
    SYNTAX      Integer32 (-1 | 1..800000000)

THPolVirtualScheCIRRate          ::= TEXTUAL-CONVENTION
    STATUS      current
    DESCRIPTION
        "The CIR rate to be used in kbps. The value -1 means maximum rate."
    SYNTAX      Integer32 (-1 | 0..800000000)

TAdvCfgRate                      ::= TEXTUAL-CONVENTION
    STATUS      current
    DESCRIPTION
        "The PIR rate to be used in kbps."
    SYNTAX      Integer32 (0..100000000)

TMaxDecRate                      ::= TEXTUAL-CONVENTION
    STATUS      current
    DESCRIPTION
        "The Advanced Configuration policy Max-Decrement rate to be used in
         kbps."
    SYNTAX      Integer32 (0 | 1..100000000)

THPolPIRRate                     ::= TEXTUAL-CONVENTION
    STATUS      current
    DESCRIPTION
        "The PIR rate to be used in kbps. The value -1 means maximum rate."
    SYNTAX      Integer32 (-1 | 1..2000000000)

TSecondaryShaper10GPIRRate       ::= TEXTUAL-CONVENTION
    STATUS      current
    DESCRIPTION
        "The secondary shaper PIR rate to be used in Mbps. The value -1 means
         maximum rate."
    SYNTAX      Integer32 (-1 | 1..10000)

TExpSecondaryShaperPIRRate       ::= TEXTUAL-CONVENTION
    STATUS      current
    DESCRIPTION
        "The expanded secondary shaper PIR rate to be used in Kbps. The value
         -1 means maximum rate."
    SYNTAX      Integer32 (-1 | 1..10000000)

TExpSecondaryShaperClassRate     ::= TEXTUAL-CONVENTION
    STATUS      current
    DESCRIPTION
        "The expanded secondary shaper class PIR rate to be used in Kbps. The
         value -1 means maximum rate."
    SYNTAX      Integer32 (-1 | 1..10000000)

TPIRRateOverride                 ::= TEXTUAL-CONVENTION
    STATUS      current
    DESCRIPTION
        "The PIR rate to be used in kbps. The value -1 means maximum rate. A
         value of -2 specifies no override."
    SYNTAX      Integer32 (-2 | -1 | 1..100000000)

TPIRAggRateLimitOverride         ::= TEXTUAL-CONVENTION
    STATUS      current
    DESCRIPTION
        "The PIR rate to be used in kbps. The value -1 means maximum rate. A
         value of -2 specifies no override."
    SYNTAX      Integer32 (-2 | -1 | 1..800000000)

THPolPIRRateOverride             ::= TEXTUAL-CONVENTION
    STATUS      current
    DESCRIPTION
        "The PIR rate to be used in kbps. The value -1 means maximum rate. A
         value of -2 specifies no override."
    SYNTAX      Integer32 (-2 | -1 | 1..2000000000)

TPIRPercentOverride              ::= TEXTUAL-CONVENTION
    STATUS      current
    DESCRIPTION
        "The PIR percentage rate specified in centipercent. A value of -2
         specifies no override."
    SYNTAX      Integer32 (-2 | 1..10000)

TPIRRateOrZero                   ::= TEXTUAL-CONVENTION
    STATUS      current
    DESCRIPTION
        "The PIR rate to be used in kbps. The value -1 means maximum rate. The
         value 0 means undefined rate."
    SYNTAX      Integer32 (-1 | 0..100000000)

THsmdaPIRKRate                   ::= TEXTUAL-CONVENTION
    STATUS      current
    DESCRIPTION
        "The HSMDA PIR rate to be used in Kbps. The value -1 means maximum
         rate."
    SYNTAX      Integer32 (-1 | 1..100000000)

THsmdaPIRKRateOverride           ::= TEXTUAL-CONVENTION
    STATUS      current
    DESCRIPTION
        "The HSMDA PIR rate to be used in Kbps. The value -1 means maximum
         rate. A value of -2 specifies no override."
    SYNTAX      Integer32 (-2 | -1 | 1..100000000)

THsmdaPIRMRate                   ::= TEXTUAL-CONVENTION
    STATUS      current
    DESCRIPTION
        "The HSMDA PIR rate to be used in Mbps. The value -1 means maximum
         rate."
    SYNTAX      Integer32 (-1 | 1..100000)

THsmdaPIRMRateOverride           ::= TEXTUAL-CONVENTION
    STATUS      current
    DESCRIPTION
        "The HSMDA PIR rate to be used in Mbps. The value -1 means maximum
         rate. A value of -2 specifies no override."
    SYNTAX      Integer32 (-2 | -1 | 1..100000)

TmnxDHCP6MsgType                 ::= TEXTUAL-CONVENTION
    STATUS      current
    DESCRIPTION
        "The DHCP6 messagetype."
    SYNTAX      INTEGER {
        dhcp6MsgTypeSolicit         (1),
        dhcp6MsgTypeAdvertise       (2),
        dhcp6MsgTypeRequest         (3),
        dhcp6MsgTypeConfirm         (4),
        dhcp6MsgTypeRenew           (5),
        dhcp6MsgTypeRebind          (6),
        dhcp6MsgTypeReply           (7),
        dhcp6MsgTypeRelease         (8),
        dhcp6MsgTypeDecline         (9),
        dhcp6MsgTypeReconfigure     (10),
        dhcp6MsgTypeInfoRequest     (11),
        dhcp6MsgTypeRelayForw       (12),
        dhcp6MsgTypeRelayReply      (13),
        dhcp6MsgTypeLeasequery      (14),
        dhcp6MsgTypeLeasequeryReply (15)
    }

TmnxDhcpClientState              ::= TEXTUAL-CONVENTION
    STATUS      current
    DESCRIPTION
        "The state of a DHCP client."
    SYNTAX      INTEGER {
        init        (0),
        init-reboot (1),
        rebooting   (2),
        selecting   (3),
        requesting  (4),
        rebinding   (5),
        bound       (6),
        renewing    (7)
    }

TmnxIgpInstance                  ::= TEXTUAL-CONVENTION
    STATUS      current
    DESCRIPTION
        "An object of type TmnxIgpInstance identifies an instance of an
         Interior Gateway Protocol (IGP).

         Supported IGPs are Intermediate System to Intermediate System (IS-IS)
         and Open Shortest Path First (OSPF).

         The supported range varies with the IGP and address family, as
         follows.

         IGP      Address Family   Supported Range
         ------   --------------   ---------------
         IS-IS    all                        0..127
         OSPFv2   all                        0..31
         OSPFv3   IPv4 unicast              64..95
         OSPFv3   IPv6 unicast               0..31 "
    REFERENCE
        "RFC 5838, 'Support of Address Families in OSPFv3', Section 2.1,
         'Instance ID Values for New AFs'."
    SYNTAX      Unsigned32 (0..127)

TmnxOspfInstance                 ::= TEXTUAL-CONVENTION
    STATUS      current
    DESCRIPTION
        "A number used to identify an instance of OSPF,

         For OSPFv2 only 0..31 is supported,

         For OSPFv3 the range is divided in address families as follows:

           0..31   ipv6-unicast address family (supported)
           32..63  ipv6-multicast address family (not supported)
           64..95  ipv4-unicast address family (supported)
           96..127 ipv4-multicast address family (not supported)"
    SYNTAX      Unsigned32 (0..127)

TmnxBGPFamilyType                ::= TEXTUAL-CONVENTION
    STATUS      current
    DESCRIPTION
        "The value of TmnxBGPFamilyType specifies the AFI-SAFI family for BGP
         peer."
    SYNTAX      BITS {
        ipv4Unicast    (0),
        ipv4Multicast  (1),
        ipv4UastMcast  (2),
        ipv4MplsLabel  (3),
        ipv4Vpn        (4),
        ipv6Unicast    (5),
        ipv6Multicast  (6),
        ipv6UcastMcast (7),
        ipv6MplsLabel  (8),
        ipv6Vpn        (9),
        l2Vpn          (10),
        ipv4Mvpn       (11),
        msPw           (12),
        ipv4Flow       (13),
        mdtSafi        (14),
        routeTarget    (15),
        mcastVpnIpv4   (16),
        mvpnIpv6       (17),
        ipv6Flow       (18),
        evpn           (19),
        bgpLs          (20),
        mcastVpnIpv6   (21),
        srplcyIpv4     (22),
        srplcyIpv6     (23),
        flowVpnIpv4    (24),
        flowVpnIpv6    (25)
    }

TmnxIgmpGroupFilterMode          ::= TEXTUAL-CONVENTION
    STATUS      current
    DESCRIPTION
        "The data type TmnxIgmpGroupFilterMode describes the filter-mode of a
         group.

         In 'include(1)' mode, reception of packets sent to the specified
         multicast address is requested only from those IPv4 Source addresses
         listed in the corresponding source-list.

         In 'exclude(2)' mode, reception of packets sent to the given multicast
         address is requested from all IPv4 Source addresses, except those
         listed in the corresponding source-list (if any)."
    SYNTAX      INTEGER {
        include (1),
        exclude (2)
    }

TmnxIgmpGroupType                ::= TEXTUAL-CONVENTION
    STATUS      current
    DESCRIPTION
        "The data type TmnxIgmpGroupType describes how a multicast group is
         learned."
    SYNTAX      INTEGER {
        static   (1),
        dynamic  (2),
        bgp-smet (3),
        bgp-sync (4)
    }

TmnxIgmpSnpgGroupType            ::= TEXTUAL-CONVENTION
    STATUS      current
    DESCRIPTION
        "The data type TmnxIgmpSnpgGroupType describes how a multicast group is
         learned."
    SYNTAX      INTEGER {
        static   (1),
        dynamic  (2),
        bgp-smet (3),
        bgp-sync (4)
    }

TmnxIgmpVersion                  ::= TEXTUAL-CONVENTION
    STATUS      current
    DESCRIPTION
        "The data type TmnxIgmpVersion denotes the version of the IGMP protocol:
         - 'version1(1)': means version 1 of the IGMP protocol
         - 'version2(2)': means version 2 of the IGMP protocol
         - 'version3(3)': means version 3 of the IGMP protocol."
    SYNTAX      INTEGER {
        version1 (1),
        version2 (2),
        version3 (3)
    }

TmnxMldGroupFilterMode           ::= TEXTUAL-CONVENTION
    STATUS      current
    DESCRIPTION
        "The data type TmnxMldGroupFilterMode describes the filter-mode of a
         group.

         In 'include(1)' mode, reception of packets sent to the specified
         multicast address is requested only from those IPv6 source addresses
         listed in the corresponding source-list.

         In 'exclude(2)' mode, reception of packets sent to the given multicast
         address is requested from all IPv6 source addresses, except those
         listed in the corresponding source-list (if any)."
    SYNTAX      INTEGER {
        include (1),
        exclude (2)
    }

TmnxMldGroupType                 ::= TEXTUAL-CONVENTION
    STATUS      current
    DESCRIPTION
        "The data type TmnxMldGroupType describes how a multicast group is
         learned."
    SYNTAX      INTEGER {
        static   (1),
        dynamic  (2),
        bgp-smet (3),
        bgp-sync (4)
    }

TmnxMldVersion                   ::= TEXTUAL-CONVENTION
    STATUS      current
    DESCRIPTION
        "The data type TmnxMldVersion denotes the version of the MLD protocol:
         - 'version1(1)': means version 1 of the MLD protocol
         - 'version2(2)': means version 2 of the MLD protocol"
    SYNTAX      INTEGER {
        version1 (1),
        version2 (2)
    }

TmnxManagedRouteStatus           ::= TEXTUAL-CONVENTION
    STATUS      current
    DESCRIPTION
        "The data type TmnxManagedRouteStatus denotes the status of a Managed
         Route."
    SYNTAX      INTEGER {
        installed               (0),
        notYetInstalled         (1),
        wrongAntiSpoofType      (2),
        outOfMemory             (3),
        shadowed                (4),
        routeTableFull          (5),
        parentInterfaceDown     (6),
        hostInactive            (7),
        enhancedSubMgmtRequired (8),
        deprecated1             (9),
        l2AwNotSupported        (10),
        nextHopLimitExceeded    (11),
        notApplicable           (12),
        noNextHop               (13),
        gtpNotSupported         (14),
        withdrawn               (15)
    }

TmnxTunnelTypeExt                ::= TEXTUAL-CONVENTION
    STATUS      current
    DESCRIPTION
        "The type of this tunnel entity."
    SYNTAX      INTEGER {
        invalid       (1),
        sdp           (2),
        rsvp          (3),
        ldp           (4),
        ospf          (5),
        isis          (6),
        bypass        (7),
        gre           (8),
        bgp           (9),
        srTe          (10),
        fpe           (11),
        udp           (12),
        ospfV3        (13),
        mplsFwdPolicy (14),
        srPolicy      (15),
        ribApi        (16),
        bgpEpe        (17),
        srv6Isis      (18),
        srv6Policy    (19),
        srv6          (20)
    }

TmnxIgpSCFamilyType              ::= TEXTUAL-CONVENTION
    STATUS      current
    DESCRIPTION
        "The data type to specify IGP shortcut tunnel next hop family."
    SYNTAX      INTEGER {
        ipv4 (0),
        ipv6 (1),
        srv4 (2),
        srv6 (3)
    }

TmnxAdjacencySetFamilyType       ::= TEXTUAL-CONVENTION
    STATUS      current
    DESCRIPTION
        "The data type to specify Adjacency Set family."
    SYNTAX      INTEGER {
        ipv4 (0),
        ipv6 (1)
    }

TmnxAncpString                   ::= TEXTUAL-CONVENTION
    STATUS      current
    DESCRIPTION
        "The TmnxAncpString data type contains a valid ancp string."
    SYNTAX      DisplayString (SIZE (1..63))

TmnxAncpStringOrZero             ::= TEXTUAL-CONVENTION
    STATUS      current
    DESCRIPTION
        "The TmnxAncpStringOrZero data type contains a valid ancp string. An
         empty string indicates that no ANCP string is defined."
    SYNTAX      DisplayString (SIZE (0..63))

TmnxMulticastAddrFamily          ::= TEXTUAL-CONVENTION
    STATUS      current
    DESCRIPTION
        "The data type TmnxMulticastAddrFamily denotes the family for multicast
         protocol."
    SYNTAX      INTEGER {
        ipv4Multicast (0),
        ipv6Multicast (1)
    }

TmnxNatIsaGrpId                  ::= TEXTUAL-CONVENTION
    STATUS      current
    DESCRIPTION
        "The TmnxNatIsaGrpId data type contains an identification number for a
         Network Address Translation Integrated Service Adaptor group."
    SYNTAX      Unsigned32 (1..4)

TmnxNatIsaGrpIdOrZero            ::= TEXTUAL-CONVENTION
    STATUS      current
    DESCRIPTION
        "The TmnxNatIsaGrpIdOrZero data type contains an identification number
         for a Network Address Translation Integrated Service Adaptor (ISA)
         group.

         The value zero means that no NAT ISA Group is defined."
    SYNTAX      Unsigned32 (0..4)

TmnxNatL2AwAccessMode            ::= TEXTUAL-CONVENTION
    STATUS      current
    DESCRIPTION
        "TmnxNatL2AwAccessMode is an enumerated integer that specifies the
         Layer-2-Aware NAT access mode.

         The value 'auto' means that the system automatically derives the
         access mode from the configuration (of the access SAP)."
    SYNTAX      INTEGER {
        auto    (1),
        bridged (2)
    }

TmnxNatSubscriberType            ::= TEXTUAL-CONVENTION
    STATUS      current
    DESCRIPTION
        "TmnxNatSubscriberType is an enumerated integer that specifies the NAT
         subscriber type.

         The possible values are 'classicLsnSub' and 'dsliteLsnSub' for classic
         and Dual Stack Lite Large Scale NAT subscribers respectively,
         'l2AwareSub' for Layer-2-Aware NAT subscribers, and 'nat64LsnSub' for
         NAT-64 subscribers respectively."
    SYNTAX      INTEGER {
        l2AwareSub    (1),
        classicLsnSub (2),
        dsliteLsnSub  (3),
        nat64LsnSub   (4)
    }

TmnxNatSubscriberTypeOrNone      ::= TEXTUAL-CONVENTION
    STATUS      current
    DESCRIPTION
        "TmnxNatSubscriberTypeOrNone is an enumerated integer that specifies
         the NAT subscriber type.

         The value 'none' indicates that NAT subscriber type is not specified.

         The values 'classicLsnSub' and 'dsliteLsnSub' are for classic and Dual
         Stack Lite Large Scale NAT subscribers respectively. The value
         'l2AwareSub' is for Layer-2-Aware NAT subscribers, and the value
         'nat64LsnSub' is for NAT-64 subscribers."
    SYNTAX      INTEGER {
        none          (0),
        l2AwareSub    (1),
        classicLsnSub (2),
        dsliteLsnSub  (3),
        nat64LsnSub   (4)
    }

TmnxNatWaterMark                 ::= TEXTUAL-CONVENTION
    STATUS      current
    DESCRIPTION
        "The TmnxNatWaterMark data type contains an unsigned number that marks
         a usage level in percent.

         The value zero means that no watermark is defined."
    SYNTAX      Unsigned32 (0..100)

TmnxAuthPassword                 ::= TEXTUAL-CONVENTION
    STATUS      current
    DESCRIPTION
        "The TmnxAuthPassword data type contains a password used for
         authentication of subscribers."
    SYNTAX      DisplayString (SIZE (0..64))

TmnxAsciiSpecification           ::= TEXTUAL-CONVENTION
    STATUS      current
    DESCRIPTION
        "The data type TmnxAsciiSpecification is a format string that specifies
         how to form a target ASCII string.

         The format is as follows:

         <ascii-specification> ::= <char-specification>+

         <char-specification>  ::= <ascii-char> | <char-origin>

         <char-origin>         ::= '%' <origin>

         <ascii-char> refers to a printable ASCII character.

         Examples and supported char-origin specifiers are supplied with the
         object definitions."
    SYNTAX      DisplayString (SIZE (0..255))

TmnxMacSpecification             ::= TEXTUAL-CONVENTION
    STATUS      current
    DESCRIPTION
        "The data type TmnxMacSpecification is a string of ASCII characters
         that specifies how to format a string that represents a MAC address.

         The format is as follows:

         <mac-specification> ::= <alpha-string> [<delimiter-char>]

         <alpha-string>      ::= <ucase-alpha>+ | <lcase-alpha>+
         <ucase-alpha>       ::= 'A' | 'B' | 'B' ... | 'Z'
         <lcase-alpha>       ::= 'a' | 'b' | 'c' ... | 'z'

         <delimiter-char>    any ASCII character that is not an <alpha-char>
                            or a decimal digit

         Only the number of alphabetic characters and the case is relevant.
         Examples:

         'ab:'               00:0c:f1:99:85:b8  Nokia SROS style
         'XY-'               00-0C-F1-99-85-B8  IEEE canonical style
         'mmmm.'             0002.03aa.abff     Cisco style.
         'xx'                000cf19985b8"
    SYNTAX      DisplayString (SIZE (0..17))

TmnxBinarySpecification          ::= TEXTUAL-CONVENTION
    STATUS      current
    DESCRIPTION
        "The data type TmnxBinarySpecification is a string of ASCII characters
         that specifies how to form a binary number.

         The format is as follows:

         <binary-specification> ::= <bit-specification>+

         <bit-specification>    ::= '0' | '1' | <bit-origin>

         <bit-origin>           ::= '*' <number-of-bits> <origin>

         <number-of-bits>       ::= [1..32]

         Examples and supported bit-origin specifiers are supplied with the
         object definitions."
    SYNTAX      DisplayString (SIZE (0..255))

TmnxDefSubIdSource               ::= TEXTUAL-CONVENTION
    STATUS      current
    DESCRIPTION
        "The data type TmnxDefSubIdSource specifies what will be used as the
         default subscriber identification.

         This value is used in case no other source (like RADIUS) provides a
         subscriber identification string.

         If the value of this object is set to 'useSapId', the SAP-id will be
         used as the default subscriber identification string.

         If the value of this object is set to 'useAutoId', the auto-generated
         subscriber identification string, as defined in
         tmnxSubMgmtAutoSubIdObjs, is used as the default subscriber
         identification string.

         If the value of this object is set to 'useString', the value of the
         string contained in another object will be used as the default
         subscriber identification string; that object must be identified where
         this datatype is used."
    SYNTAX      INTEGER {
        useSapId  (1),
        useString (2),
        useAutoId (3)
    }

TmnxSubAuthPlcyUserNameOp        ::= TEXTUAL-CONVENTION
    STATUS      current
    DESCRIPTION
        "The TmnxSubAuthPlcyUserNameOp data type is an enumerated integer that
         specifies the operation to perform on the user-name before sending it
         to the RADIUS server."
    SYNTAX      INTEGER {
        noOperation   (0),
        appendDomain  (1),
        stripDomain   (2),
        replaceDomain (3),
        defaultDomain (4)
    }

TmnxSubCallingStationIdType      ::= TEXTUAL-CONVENTION
    STATUS      current
    DESCRIPTION
        "The TmnxSubCallingStationIdType data type is an enumerated integer that
         specifies what string will be put in the RADIUS or DIAMETER Calling-Station-Id
         attribute:
         - sapString (1): the value of TIMETRA-SAP-MIB::sapCallingStationId of
                          the subscriber host SAP;
         - mac       (2): the subscriber host MAC address, formatted as a
                          lower case ASCII string with octet values
                          separated by a ':';
         - sapId     (3): the subscriber host SAP identifier, formatted as
                          an ASCII string.
         - remoteId  (4): the intermediate agent Remote ID as received by means
                          of, for example, a PPPoE vendor-specific tag,
                          a DHCP Agent Remote ID Sub-option or
                          an L2TP Access Line Agent-Remote-Id AVP.
         - llid      (5): the logical link identifier as received during
                          pre-authentication."
    SYNTAX      INTEGER {
        sapString (1),
        mac       (2),
        sapId     (3),
        remoteId  (4),
        llid      (5)
    }

TmnxSubAcctSessionId             ::= TEXTUAL-CONVENTION
    STATUS      current
    DESCRIPTION
        "The data type TmnxSubAcctSessionId contains a string that identifies a
         subscriber for the purposes of accounting."
    SYNTAX      DisplayString (SIZE (0..22))

TmnxSubHostGrouping              ::= TEXTUAL-CONVENTION
    STATUS      current
    DESCRIPTION
        "The TmnxSubHostGrouping data type is an enumerated integer that
         indicates the way hosts associated with a given subscriber and SAP are
         grouped together to share an SLA profile instance."
    SYNTAX      INTEGER {
        perSap         (1),
        perGroup       (2),
        perSessionPpp  (3),
        perSessionIpoe (4),
        perSessionPfcp (5)
    }

TmnxSubIdentString               ::= TEXTUAL-CONVENTION
    STATUS      current
    DESCRIPTION
        "The data type TmnxSubIdentString denotes the subscriber identification
         string."
    SYNTAX      DisplayString (SIZE (1..64))

TmnxSubIdentStringOrEmpty        ::= TEXTUAL-CONVENTION
    STATUS      current
    DESCRIPTION
        "The data type TmnxSubIdentStringOrEmpty denotes the subscriber
         identification string. The empty string denotes the absence of a
         subscriber identification string."
    SYNTAX      DisplayString (SIZE (0..64))

TmnxSubIdentShortString          ::= TEXTUAL-CONVENTION
    STATUS      current
    DESCRIPTION
        "The data type TmnxSubIdentShortString denotes the short subscriber
         identification string."
    SYNTAX      DisplayString (SIZE (1..32))

TmnxSubRadServAlgorithm          ::= TEXTUAL-CONVENTION
    STATUS      current
    DESCRIPTION
        "The TmnxSubRadServAlgorithm data type is an enumerated integer that
         indicates the algorithm used to access the list of configured RADIUS
         servers:
         - direct     (1): The first server will be used as primary server for
                            all requests, the second as secondary and so on.
         - roundRobin (2): The first server will be used as primary server for
                            the first request, the second server as primary for
                            the second request, and so on. If the router gets
                            to the end of the list, it starts again with the
                            first server.
         - hashBased  (3): The server will be selected based on a specified
                            hash value."
    SYNTAX      INTEGER {
        direct     (1),
        roundRobin (2),
        hashBased  (3)
    }

TmnxSubRadIsaServAlgorithm       ::= TEXTUAL-CONVENTION
    STATUS      current
    DESCRIPTION
        "The TmnxSubRadIsaServAlgorithm data type is an enumerated integer that
         indicates the algorithm used to access the list of configured RADIUS
         servers:
         - direct         (1): The first server will be used as primary server for
                                all requests, the second as secondary and so on.
         - roundRobin     (2): The first server will be used as primary server for
                                the first request, the second server as primary for
                                the second request, and so on. If the router gets
                                to the end of the list, it starts again with the
                                first server.
         - hashBased      (3): The server will be selected based on a specified
                                hash value.
         - directPriority (4): The first server will be used as primary server for
                                all requests, the second as secondary and so on.
                                Higher priority servers that are operationally down
                                will be probed and put back into service upon a
                                response."
    SYNTAX      INTEGER {
        direct         (1),
        roundRobin     (2),
        hashBased      (3),
        directPriority (4)
    }

TmnxSubRadiusAttrType            ::= TEXTUAL-CONVENTION
    STATUS      current
    DESCRIPTION
        "The TmnxSubRadiusAttrType data type contains a number that indicates a
         RADIUS attribute type."
    REFERENCE
        "RFC 2865 Remote Authentication Dial In User Service (RADIUS)
         section 5. Attributes"
    SYNTAX      Unsigned32 (0..255)

TmnxSubRadiusVendorId            ::= TEXTUAL-CONVENTION
    STATUS      current
    DESCRIPTION
        "The TmnxSubRadiusVendorId data type contains a number that indicates a
         RADIUS Vendor-Id."
    REFERENCE
        "RFC 2865 Remote Authentication Dial In User Service (RADIUS)
         section 5.26. Vendor-Specific."
    SYNTAX      Unsigned32 (0..16777215)

TmnxSubRadiusDisplayString       ::= TEXTUAL-CONVENTION
    STATUS      current
    DESCRIPTION
        "The TmnxSubRadiusOctetString data type contains a character string
         that corresponds to a Radius attribute."
    REFERENCE
        "RFC 2865 Remote Authentication Dial In User Service (RADIUS)
         section 5.  Attributes."
    SYNTAX      DisplayString (SIZE (0..253))

TmnxSubRadiusOctetString         ::= TEXTUAL-CONVENTION
    STATUS      current
    DESCRIPTION
        "The TmnxSubRadiusOctetString data type contains an octet string that
         corresponds to a Radius attribute"
    REFERENCE
        "RFC 2865 Remote Authentication Dial In User Service (RADIUS)
         section 5.26. Vendor-Specific."
    SYNTAX      OCTET STRING (SIZE (253))

TmnxSubSlaMode                   ::= TEXTUAL-CONVENTION
    STATUS      current
    DESCRIPTION
        "The TmnxSubSlaMode data type is an enumerated integer that specifies
         the handling of SLA profile instances for a subscriber.
         - Expanded sla-mode: a subscriber is allowed to have multiple SLA
           profile instances, using different SLA profiles and/or different
           VLANs.
         - Single sla-mode: only 1 single SLA profile instance is allowed for a
           subscriber. This restriction has 2 implications:
           - Last SLA profile wins: if a new host is added with an SLA profile
             that is different from the existing hosts of the subscriber, or an
             existing host is changed to use a different SLA profile, then all
             existing hosts of that subscriber will be changed to the new SLA
             profile.
           - First VLAN wins: All hosts of a subscriber must use the same VLAN,
             i.e. a new host on different VLAN is rejected."
    SYNTAX      INTEGER {
        expanded (0),
        single   (1)
    }

TmnxRadiusPendingReqLimit        ::= TEXTUAL-CONVENTION
    STATUS      current
    DESCRIPTION
        "The TmnxRadiusPendingReqLimit data type is a number that specifies the
         limit to the number of pending RADIUS request messages."
    SYNTAX      Unsigned32 (1..4096)

TmnxRadiusServerOperState        ::= TEXTUAL-CONVENTION
    STATUS      current
    DESCRIPTION
        "The TmnxRadiusServerOperState data type is an enumerated integer that
         describes the values used to identify the operational state of a
         RADIUS server."
    SYNTAX      INTEGER {
        unknown      (1),
        inService    (2),
        outOfService (3),
        transition   (4),
        overloaded   (5),
        probing      (6)
    }

TmnxSubShcvAction                ::= TEXTUAL-CONVENTION
    STATUS      current
    DESCRIPTION
        "The TmnxSubShcvAction data type is an enumerated integer that
         describes the values used to identify the action taken when Subscriber
         Host Connectivity Verification (SHCV) failed."
    SYNTAX      INTEGER {
        alarm  (1),
        remove (2)
    }

TmnxSubShcvInterval              ::= TEXTUAL-CONVENTION
    STATUS      current
    DESCRIPTION
        "The TmnxSubShcvInterval data type is a number that specifies the
         interval in minutes between connectivity checks.

         The value zero means no connectivity checking."
    SYNTAX      Unsigned32 (0..6000)

TmnxSubShcvRetryCount            ::= TEXTUAL-CONVENTION
    STATUS      current
    DESCRIPTION
        "The TmnxSubShcvRetryTimeout data type is a number that specifies the
         number of connectivity check retransmissions.

         Setting the value to n specifies that, for any given host, at most
         (n+1) probes are done each interval, and (n+1) missed replies are
         considered as a connectivity failure."
    SYNTAX      Unsigned32 (2..29)

TmnxSubShcvRetryTimeout          ::= TEXTUAL-CONVENTION
    STATUS      current
    DESCRIPTION
        "The TmnxSubShcvRetryTimeout data type is a number that specifies the
         timeout in seconds before a connectivity check retransmission."
    SYNTAX      Unsigned32 (10..60)

TmnxSubShcvSrcIpOrigin           ::= TEXTUAL-CONVENTION
    STATUS      current
    DESCRIPTION
        "The TmnxSubShcvSrcIpOrigin data type is an enumerated integer that
         describes the values used to identify the origin of the source IP
         address used for connectivity verification in a layer-3 service (IES
         or VPRN).

         The value 'interface' means that the IP address of the interface is
         used.

         The value 'vrrp' means that the primary IP address of the Virtual
         Router Redundancy Protocol (VRRP) is used."
    SYNTAX      INTEGER {
        interface (1),
        vrrp      (2)
    }

TmnxSubSpiGroupId                ::= TEXTUAL-CONVENTION
    STATUS      current
    DESCRIPTION
        "The TmnxSubSpiGroupId data type is an integer that specifies the SLA
         profile instance group identifier.

         A value of minus one means that there is no group identifier
         configured."
    SYNTAX      Integer32 (-1..65535)

TmnxSubOperSpiGroupId            ::= TEXTUAL-CONVENTION
    STATUS      current
    DESCRIPTION
        "The TmnxSubOperSpiGroupId data type is an integer that indicates the
         SLA profile instance group identifier specified by the AAA server.

         A value of minus one indicates that the AAA server did not specify
         such a group identifier."
    SYNTAX      Integer32

TmnxReferenceBandwidth           ::= TEXTUAL-CONVENTION
    STATUS      current
    DESCRIPTION
        "The TmnxRadiusPendingReqLimit data type is a number that specifies the
         reference bandwidth used for cost calculation.

         The formula is:  Cost = reference-bandwidth / bandwidth.

         The unit is 1000 bps.

         The value zero specifies that no reference-bandwidth is configured."
    SYNTAX      Unsigned32 (0..4000000000)

TmnxSubPfcpNodeIdType            ::= TEXTUAL-CONVENTION
    STATUS      current
    DESCRIPTION
        "The TmnxSubPfcpNodeIdType data type is an enumerated integer that
         describes the values used to identify a PFCP node.

         The value 'useIpAddress' means that an IP address is used.

         The value 'fqdn' means that a Fully Qualified Domain Name (FQDN) is
         used."
    SYNTAX      INTEGER {
        none         (0),
        useIpAddress (1),
        fqdn         (2)
    }

TmnxSubPfcpNodeIdDomainName      ::= TEXTUAL-CONVENTION
    STATUS      current
    DESCRIPTION
        "A Fully Qualified Domain Name."
    SYNTAX      DisplayString (SIZE (0..255))

TmnxSubPfcpPeerNodeIdType        ::= TEXTUAL-CONVENTION
    STATUS      current
    DESCRIPTION
        "The TmnxSubPfcpPeerNodeIdType data type is an enumerated integer that
         describes the values used to identify a PFCP peer node.

         The value 'useIpAddress' means that an IP address is used.

         The value 'fqdn' means that a Fully Qualified Domain Name (FQDN) is
         used."
    SYNTAX      INTEGER {
        none         (0),
        useIpAddress (1),
        reserved2    (2)
    }

TmnxSubPfcpCurrPeerNodeIdType    ::= TEXTUAL-CONVENTION
    STATUS      current
    DESCRIPTION
        "The TmnxSubPfcpCurrPeerNodeIdType data type is an enumerated integer
         that describes the values used to identify a PFCP peer node.

         The value 'none' means that the peer nodeId is not yet known.

         The value 'useIpAddress' means that an IP address is used.

         The value 'fqdn' means that a Fully Qualified Domain Name (FQDN) is
         used."
    SYNTAX      INTEGER {
        none         (0),
        useIpAddress (1),
        fqdn         (2)
    }

TmnxSubPfcpPeerSystemNodeIdType  ::= TEXTUAL-CONVENTION
    STATUS      current
    DESCRIPTION
        "The TmnxSubPfcpPeerSystemNodeIdType data type is an enumerated integer
         that describes the values used to identify a PFCP peer node id.

         The value 'useIpAddress' means that an IP address is used.

         The value 'fqdn' means that a Fully Qualified Domain Name (FQDN) is
         used."
    SYNTAX      INTEGER {
        useIpAddress (1),
        fqdn         (2)
    }

TmnxSubPoolName                  ::= TEXTUAL-CONVENTION
    STATUS      current
    DESCRIPTION
        "The name of a pool"
    SYNTAX      TLNamedItem

TmnxSubProfileString             ::= TEXTUAL-CONVENTION
    STATUS      current
    DESCRIPTION
        "The data type TmnxSubProfileString denotes the subscriber profile
         string."
    SYNTAX      DisplayString (SIZE (1..32))

TmnxSubProfileStringOrEmpty      ::= TEXTUAL-CONVENTION
    STATUS      current
    DESCRIPTION
        "The data type TmnxSubProfileStringOrEmpty denotes the subscriber
         profile string. The empty string denotes the absence of a subscriber
         profile."
    SYNTAX      DisplayString (SIZE (0..32))

TmnxSlaProfileString             ::= TEXTUAL-CONVENTION
    STATUS      current
    DESCRIPTION
        "The data type TmnxSlaProfileString denotes the SLA profile string."
    SYNTAX      DisplayString (SIZE (1..32))

TmnxSlaProfileStringOrEmpty      ::= TEXTUAL-CONVENTION
    STATUS      current
    DESCRIPTION
        "The data type TmnxSlaProfileStringOrEmpty denotes the SLA profile
         string. The empty string denotes the absence of a SLA profile."
    SYNTAX      DisplayString (SIZE (0..32))

TmnxAppProfileString             ::= TEXTUAL-CONVENTION
    STATUS      current
    DESCRIPTION
        "The data type TmnxAppProfileString denotes the application profile
         string."
    SYNTAX      DisplayString (SIZE (1..32))

TmnxAppProfileStringOrEmpty      ::= TEXTUAL-CONVENTION
    STATUS      current
    DESCRIPTION
        "The data type TmnxAppProfileStringOrEmpty denotes the application
         profile string. The empty string denotes the absence of a application
         profile."
    SYNTAX      DisplayString (SIZE (0..32))

TmnxSubMgtIntDestIdOrEmpty       ::= TEXTUAL-CONVENTION
    STATUS      current
    DESCRIPTION
        "The data type TmnxSubMgtIntDestIdOrEmpty denotes the intermediate
         destination id. The empty string denotes the absence of an
         intermediate destination id."
    SYNTAX      DisplayString (SIZE (0..32))

TmnxSubMgtIntDestId              ::= TEXTUAL-CONVENTION
    STATUS      current
    DESCRIPTION
        "The data type TmnxSubMgtIntDestId denotes the intermediate destination
         id."
    SYNTAX      TmnxSubMgtIntDestIdOrEmpty (SIZE (1..32))

TmnxDefInterDestIdSource         ::= TEXTUAL-CONVENTION
    STATUS      current
    DESCRIPTION
        "The data type TmnxDefInterDestIdSource specifies what will be used as
         the default intermediate destination identifier.

         This value is used in case no other source (like RADIUS) provides an
         intermediate destination identifier.

         If the value of this object is set to 'useString', the value of the
         string contained in another object will be used as the default
         intermediate destination identifier; that object must be identified
         where this datatype is used.

         If the value of this object is set to 'useTopQTag', the top q-tag of
         the ingress SAP will be used as the default subscriber intermediate
         destination identifier.

         If the value of this object is set to 'useVpi', the ATM VPI of the
         ingress SAP will be used as the default subscriber intermediate
         destination identifier."
    SYNTAX      INTEGER {
        useString  (1),
        useTopQTag (2),
        useVpi     (3)
    }

TmnxSubNasPortSuffixType         ::= TEXTUAL-CONVENTION
    STATUS      current
    DESCRIPTION
        "The TmnxSubNasPortSuffixType data type is an enumerated integer that
         specifies what suffix will be added to the RADIUS NAS-Port attribute:
         - none      (0): No suffix will be added.
         - circuitId (1): If available, the circuit-id will be added.
         - remoteId  (2): If available, the remote-id will be added."
    SYNTAX      INTEGER {
        none      (0),
        circuitId (1),
        remoteId  (2)
    }

TmnxSubNasPortPrefixType         ::= TEXTUAL-CONVENTION
    STATUS      current
    DESCRIPTION
        "The TmnxSubNasPortPrefixType data type is an enumerated integer that
         specifies what prefix will be added to the RADIUS NAS-Port attribute:
         - none       (0): No prefix will be added.
         - userString (1): A user configurable string will be added."
    SYNTAX      INTEGER {
        none       (0),
        userString (1)
    }

TmnxSubNasPortTypeType           ::= TEXTUAL-CONVENTION
    STATUS      current
    DESCRIPTION
        "The TmnxSubNasPortTypeType data type is an enumerated integer that
         specifies what value will be put in the NAS-Port-Type attribute
         of RADIUS or DIAMETER messages:
         - standard  (1): according to the RADIUS specification
                          RFC 2865 section 5.41 NAS-Port-Type and
                          RFC 4603 Additional Values for the NAS-Port-Type Attribute;
         - config    (2): a configured value."
    SYNTAX      INTEGER {
        standard (1),
        config   (2)
    }

TmnxSubCreditVolumeUnit          ::= TEXTUAL-CONVENTION
    STATUS      current
    DESCRIPTION
        "The TmnxSubCreditVolumeUnit data type is an enumerated integer that
         specifies the unit in which the volume-credit is expressed."
    SYNTAX      INTEGER {
        bytes     (0),
        kilobytes (1),
        megabytes (2),
        gigabytes (3)
    }

TmnxPccRuleFilterForwardAction   ::= TEXTUAL-CONVENTION
    STATUS      current
    DESCRIPTION
        "The TmnxPccRuleFilterForwardAction data type is an enumerated integer
         that specifies the filter action taken in a PCC rule. The value
         redirNhOrFwd (5) means: forward to the specified next hop, but if no
         next-hop ip address or service id is given then just forward."
    SYNTAX      INTEGER {
        none         (0),
        forward      (1),
        drop         (2),
        redirUrl     (3),
        redirNh      (4),
        redirNhOrFwd (5),
        remarkDscp   (6)
    }

TmnxPccRuleQosForwardAction      ::= TEXTUAL-CONVENTION
    STATUS      current
    DESCRIPTION
        "The TmnxPccRuleQosForwardAction data type is an enumerated integer
         that specifies the qos action taken in a PCC rule."
    SYNTAX      BITS {
        rateLimit    (0),
        fcRemark     (1),
        monitor      (2),
        account      (3),
        forward      (4),
        insertRqiQfi (5),
        flowLimit    (6),
        flowLimit1   (7),
        l2FromProf   (8)
    }

TmnxRadiusFramedRouteMetric      ::= TEXTUAL-CONVENTION
    STATUS      current
    DESCRIPTION
        "The TmnxRadiusFramedRouteMetric data type is a number that represents
         the value of the metric in a RADIUS Framed-Route option Text field."
    SYNTAX      Unsigned32 (0..65535)

TmnxRadiusFramedRoutePreference  ::= TEXTUAL-CONVENTION
    STATUS      current
    DESCRIPTION
        "The TmnxRadiusFramedRouteMetric data type is a number that represents
         the value of the preference in a RADIUS Framed-Route option Text
         field."
    SYNTAX      Unsigned32 (0..255)

TmnxRadiusFramedRouteTag         ::= TEXTUAL-CONVENTION
    STATUS      current
    DESCRIPTION
        "The TmnxRadiusFramedRouteMetric data type is a number that represents
         the value of the tag in a RADIUS Framed-Route option Text field."
    SYNTAX      Unsigned32 (0..4294967295)

TmnxSubMgtOrgStrOrZero           ::= TEXTUAL-CONVENTION
    STATUS      current
    DESCRIPTION
        "The data type TmnxSubMgtOrgStrOrZero denotes the organization string.
         The empty string denotes the absence of an organization string."
    SYNTAX      DisplayString (SIZE (0..32))

TmnxSubMgtOrgString              ::= TEXTUAL-CONVENTION
    STATUS      current
    DESCRIPTION
        "The data type TmnxSubMgtOrgStrOrZero denotes the organization string."
    SYNTAX      TmnxSubMgtOrgStrOrZero (SIZE (1..32))

TmnxFilterProfileStringOrEmpty   ::= TEXTUAL-CONVENTION
    STATUS      current
    DESCRIPTION
        "The data type TmnxFilterProfileStringOrEmpty denotes the filter
         profile string. The empty string denotes the absence of a filter
         profile."
    SYNTAX      DisplayString (SIZE (0..16))

TmnxFpeId                        ::= TEXTUAL-CONVENTION
    STATUS      current
    DESCRIPTION
        "The data type TmnxFpeId is a number that uniquely identifies a Forward
         Path Extension (FPE)."
    SYNTAX      Unsigned32 (1..64)

TmnxFpeIdOrZero                  ::= TEXTUAL-CONVENTION
    STATUS      current
    DESCRIPTION
        "The data type TmnxFpeIdOrZero is a number that either uniquely
         identifies a Forward Path Extension (FPE), or is equal to zero."
    SYNTAX      Unsigned32 (0..64)

TmnxFpePathId                    ::= TEXTUAL-CONVENTION
    STATUS      current
    DESCRIPTION
        "The data type TmnxFpePathId is a number that uniquely identifies a
         path within a multi-path Forward Path Extension (FPE)."
    SYNTAX      Unsigned32 (1..64)

TmnxAccessLoopEncapDataLink      ::= TEXTUAL-CONVENTION
    STATUS      current
    DESCRIPTION
        "The data type TmnxAccessLoopEncapDataLink specifies the data link used
         by the subscriber on the DSL access loop."
    SYNTAX      INTEGER {
        aal5     (0),
        ethernet (1)
    }

TmnxAccessLoopEncaps1            ::= TEXTUAL-CONVENTION
    STATUS      current
    DESCRIPTION
        "The data type TmnxAccessLoopEncaps1 specifies the encapsulation used
         by the subscriber on the DSL access loop."
    SYNTAX      INTEGER {
        notAvailable         (0),
        untaggedEthernet     (1),
        singleTaggedEthernet (2)
    }

TmnxAccessLoopEncaps2            ::= TEXTUAL-CONVENTION
    STATUS      current
    DESCRIPTION
        "The data type TmnxAccessLoopEncaps2 specifies the encapsulation used
         by the subscriber on the DSL access loop."
    SYNTAX      INTEGER {
        notAvailable              (0),
        pppoaLlc                  (1),
        pppoaNull                 (2),
        ipoaLlc                   (3),
        ipoaNull                  (4),
        ethernetOverAal5LlcFcs    (5),
        ethernetOverAal5LlcNoFcs  (6),
        ethernetOverAal5NullFcs   (7),
        ethernetOverAal5NullNoFcs (8)
    }

TmnxSubAleOffsetMode             ::= TEXTUAL-CONVENTION
    STATUS      current
    DESCRIPTION
        "The data type TmnxSubAleOffsetMode specifies the way the encapsulation
         offset of the subscriber in the DSL access loop is learned by the 7xxx
         system.

         This offset is used in 7xxx egress shaping, adjusting the subscriber
         aggregate rate to account for the fixed encapsulation offset and per
         packet variable expansion of the last mile for the specific session
         used by the subscriber host.

         The value 'none' disables the adjustment.

         While the value is 'auto', the encapsulation offset will be learned
         for example from the encapsulation type value signaled in the
         Access-loop-encapsulation sub-TLV in the Vendor-Specific PPPoE Tags or
         DHCP Relay Options [rfc4679]."
    SYNTAX      INTEGER {
        none (0),
        auto (1)
    }

TmnxSubAleOffset                 ::= TEXTUAL-CONVENTION
    STATUS      current
    DESCRIPTION
        "The data type TmnxSubAleOffset specifies the encapsulation offset
         value of the subscriber in the DSL access loop as used by the 7xxx
         system.

         This offset is used in 7xxx egress shaping in order to accurately
         shape the end user payload."
    SYNTAX      INTEGER {
        none                 (0),
        pppoaLlc             (1),
        pppoaNull            (2),
        pppoeoaLlc           (3),
        pppoeoaLlcFcs        (4),
        pppoeoaLlcTagged     (5),
        pppoeoaLlcTaggedFcs  (6),
        pppoeoaNull          (7),
        pppoeoaNullFcs       (8),
        pppoeoaNullTagged    (9),
        pppoeoaNullTaggedFcs (10),
        ipoaLlc              (11),
        ipoaNull             (12),
        ipoeoaLlc            (13),
        ipoeoaLlcFcs         (14),
        ipoeoaLlcTagged      (15),
        ipoeoaLlcTaggedFcs   (16),
        ipoeoaNull           (17),
        ipoeoaNullFcs        (18),
        ipoeoaNullTagged     (19),
        ipoeoaNullTaggedFcs  (20),
        pppoe                (21),
        pppoeTagged          (22),
        ipoe                 (23),
        ipoeTagged           (24)
    }

TmnxDataFormat                   ::= TEXTUAL-CONVENTION
    STATUS      current
    DESCRIPTION
        "The data type TmnxDataFormat represents how the input data
         is specified:
         - 'ascii (2)': the data contains seven-bit ASCII characters
         - 'hex   (3)': the data contains octets. It must be displayed in
                        hexadecimal format because it contains non-printable
                        characters."
    SYNTAX      INTEGER {
        ascii (2),
        hex   (3)
    }

TmnxDhcpOptionType               ::= TEXTUAL-CONVENTION
    STATUS      current
    DESCRIPTION
        "The data type TmnxDhcpOptionType represents how the value
         of this option is encoded:
         - 'ipv4 (1)'  : this option contains an IPv4 address (4 octets)
         - 'ascii(2)'  : this option contains seven-bit ASCII characters
         - 'hex  (3)'  : this option contains octets. It must be displayed in
                         hexadecimal format because it contains non-printable
                         characters.
         - 'ipv6 (4)'  : this option contains an IPv6 address (16 octets)
         - 'domain (5)': this option contains a domain name that will be
                         encoded as specified by RFC 1035 section 3.1."
    SYNTAX      INTEGER {
        ipv4   (1),
        ascii  (2),
        hex    (3),
        ipv6   (4),
        domain (5)
    }

TmnxDhcpOptionDisplay            ::= TEXTUAL-CONVENTION
    STATUS      current
    DESCRIPTION
        "The data type TmnxDhcpOptionDisplay represents a hint of
         how the value of a DHCP option can be displayed:
         - 'default (1)'             : display the option according to the type;
         - 'hexDuration (2)'         : display the hex option as a duration;
         - 'hexNetbiosNodeType (3)'  : display the hex option as a Netbios node type.;
         - 'hexIpv4Address (4)'      : display the hex option as a list of IPv4 addresses.;
         - 'hexIpv6Address (5)'      : display the hex option as a list of IPv6 addresses."
    SYNTAX      INTEGER {
        default            (1),
        hexDuration        (2),
        hexNetbiosNodeType (3),
        hexIpv4Address     (4),
        hexIpv6Address     (5)
    }

TmnxDhcpServerDUIDTypeCode       ::= TEXTUAL-CONVENTION
    STATUS      current
    DESCRIPTION
        "The data type TmnxDhcpServerDUIDTypeCode represents the type code of
         the DHCP Unique Identifier (DUID) as specified by RFC 3315 section
         9.1."
    SYNTAX      INTEGER {
        duidEnterprise (2),
        duidLinkLocal  (3)
    }

TmnxPppoeUserName                ::= TEXTUAL-CONVENTION
    STATUS      current
    DESCRIPTION
        "The data type TmnxPppoeUserName denotes the PPPoE username."
    SYNTAX      DisplayString (SIZE (1..253))

TmnxPppoeUserNameOrEmpty         ::= TEXTUAL-CONVENTION
    STATUS      current
    DESCRIPTION
        "The data type TmnxPppoeUserNameOrEmpty denotes the PPPoE username."
    SYNTAX      DisplayString (SIZE (0..253))

TCpmProtPolicyID                 ::= TEXTUAL-CONVENTION
    STATUS      current
    DESCRIPTION
        "The data type TCpmProtPolicyID represents the identification number of
         a CPM Protection policy.

         The value '0' indicates that no CPM Protection policy is provisioned."
    SYNTAX      Unsigned32 (0..255)

TCpmProtPolicyIDOrDefault        ::= TEXTUAL-CONVENTION
    STATUS      current
    DESCRIPTION
        "The data type TCpmProtPolicyIDOrDefault represents the identification
         number of a CPM Protection policy.

         The value of '-1' indicates the system determined default value."
    SYNTAX      Integer32 (-1 | 1..255)

TMlpppQoSProfileId               ::= TEXTUAL-CONVENTION
    STATUS      current
    DESCRIPTION
        "This textual convention uniquely identifies MLPPP Bundle QoS profile
         in the ingress and egress MLPPP QoS profile tables. The value 0
         indicates default MLPPP QoS Profile as applicable to a given H/W"
    SYNTAX      Unsigned32 (0..65535)

TMcFrQoSProfileId                ::= TEXTUAL-CONVENTION
    STATUS      current
    DESCRIPTION
        "This textual convention uniquely identifies Multi-class Frame relay
         QoS profiles in the ingress and egress multi-class frame relay QoS
         profile tables. The value 0 indicates a default QoS Profile as
         applicable to a given hardware."
    SYNTAX      Unsigned32 (0..65535)

TmnxPppoeSessionId               ::= TEXTUAL-CONVENTION
    STATUS      current
    DESCRIPTION
        "The TmnxPppoeSessionId indicates the 16 bit wide PPPoE session Id."
    SYNTAX      Unsigned32 (0..65535)

TmnxPppoePadoDelay               ::= TEXTUAL-CONVENTION
    STATUS      current
    DESCRIPTION
        "The data type TmnxPppoePadoDelay specifies the delay timeout in
         deciseconds before sending a PADO (PPPoE Active Discovery Offer)."
    SYNTAX      Unsigned32 (0 | 1..30)

TmnxPppoeSessionInfoOrigin       ::= TEXTUAL-CONVENTION
    STATUS      current
    DESCRIPTION
        "The TmnxPppoeSessionInfoOrigin indicates the originator of the
         provided information."
    SYNTAX      INTEGER {
        none             (0),
        default          (1),
        radius           (2),
        localUserDb      (3),
        dhcp             (4),
        midSessionChange (5),
        tags             (6),
        l2tp             (7),
        localPool        (8),
        diameterNasreq   (9),
        diameterGx       (10),
        gtp              (11),
        python           (12),
        bonding          (13)
    }

TmnxPppoeSessionType             ::= TEXTUAL-CONVENTION
    STATUS      current
    DESCRIPTION
        "The TmnxPppoeSessionType indicates the type of PPPoE session."
    SYNTAX      INTEGER {
        local          (1),
        localWholesale (2),
        localRetail    (3),
        l2tp           (4)
    }

TmnxPppNcpProtocol               ::= TEXTUAL-CONVENTION
    STATUS      current
    DESCRIPTION
        "The TmnxPppNcpProtocol data type represents the PPP Network Control
         Protocol."
    SYNTAX      INTEGER {
        ipcp   (1),
        ipv6cp (2)
    }

TmnxDiamCcFailureHndlng          ::= TEXTUAL-CONVENTION
    STATUS      current
    DESCRIPTION
        "The TmnxDiamCcFailureHndlng data type is an enumerated integer that
         describes the different actions that can be taken after a DCCA
         (Diameter Credit Control Application) session failure has occurred."
    SYNTAX      INTEGER {
        terminate         (1),
        continue          (2),
        retryAndTerminate (3)
    }

TmnxMlpppEpClass                 ::= TEXTUAL-CONVENTION
    STATUS      current
    DESCRIPTION
        "The TmnxMlpppEpClass type represents the address class of the MLPPP
         Endpoint Discriminator option."
    SYNTAX      INTEGER {
        null            (0),
        local           (1),
        ipv4Address     (2),
        macAddress      (3),
        magicNumber     (4),
        directoryNumber (5)
    }

TNetworkPolicyID                 ::= TEXTUAL-CONVENTION
    STATUS      current
    DESCRIPTION
        "the identification number of a network policy."
    SYNTAX      TPolicyID (1..65535 | 65536 | 65537 | 65538 | 65539)

TItemScope                       ::= TEXTUAL-CONVENTION
    STATUS      current
    DESCRIPTION
        "This textual convention determines some aspects of an item's behavior
         regarding creation and use, unused entry garbage collection, and
         automated promulgation by Element Management System to other systems
         in the service domain.

         TItemScope applies to SAP-ingress, SAP-egress, and Network policies,
         and to IP filters and MAC filters.

         exclusive:

             When the scope of an item is defined as exclusive, the item can
             only be applied once, for example to a single SAP.  Attempting
             to assign the policy to a second SAP is not allowed and will
             result in an error.  If the item is removed from the exclusive
             SAP, it will become available for assignment to another
             exclusive SAP.

             A non-applied exclusive scope policy is a candidate to be removed
             from the system by a TBD garbage collection command.

             The system default policies cannot be put into the exclusive scope.
             An error will be generated if scope exclusive is executed in
             any policies with a policy-id equal to 1.

         template:

             When the scope of an item is defined as template, the item can be
             applied any number of times.  Policies with template scope
             will not be considered for deletion by a TBD garbage collection
             command; all items of scope 'template' must be deleted explicitly.

             The system default policies will always be scope template.
             An error will occur if a policy-id 1 is attempted to be
             set to scope exclusive."
    SYNTAX      INTEGER {
        exclusive (1),
        template  (2)
    }

TItemMatch                       ::= TEXTUAL-CONVENTION
    STATUS      current
    DESCRIPTION
        "when set to off, the item is not matched. when set to false, packets
         without the item match the filter. when set to true, packets with the
         item match the filter."
    SYNTAX      INTEGER {
        off   (1),
        false (2),
        true  (3)
    }

TPriority                        ::= TEXTUAL-CONVENTION
    STATUS      current
    DESCRIPTION
        "the priority to apply to a packet"
    SYNTAX      INTEGER {
        low  (1),
        high (2)
    }

TPriorityOrDefault               ::= TEXTUAL-CONVENTION
    STATUS      current
    DESCRIPTION
        "the priority to apply to a packet. when set to default(3), the
         priority from the default action is used."
    SYNTAX      INTEGER {
        low     (1),
        high    (2),
        default (3)
    }

TPriorityOrUndefined             ::= TEXTUAL-CONVENTION
    STATUS      current
    DESCRIPTION
        "the priority to apply to a packet. when set to undefined(0), the
         priority is not applicable."
    SYNTAX      INTEGER {
        undefined (0),
        low       (1),
        high      (2)
    }

TProfile                         ::= TEXTUAL-CONVENTION
    STATUS      current
    DESCRIPTION
        "the profile marking of a packet at the ingress."
    SYNTAX      INTEGER {
        in  (1),
        out (2)
    }

TProfileOrNone                   ::= TEXTUAL-CONVENTION
    STATUS      current
    DESCRIPTION
        "Profile marking of a packet."
    SYNTAX      INTEGER {
        none (0),
        in   (1),
        out  (2)
    }

TDEProfile                       ::= TEXTUAL-CONVENTION
    STATUS      current
    DESCRIPTION
        "This textual convention specifies the profile marking of a packet.

         Value of 'in' specifies the in-profile marking.

         Value of 'out' specifies the out-profile marking.

         Value of 'de' specifies that the profile marking will be based on the DE
         (Drop-Eligible) bit.  DE bit-value of '0' specifies in-profile and DE
         bit value of '1' specifies out-profile marking."
    SYNTAX      INTEGER {
        in  (1),
        out (2),
        de  (3)
    }

TEgressProfile                   ::= TEXTUAL-CONVENTION
    STATUS      current
    DESCRIPTION
        "The profile marking of a packet. Value of 'in' specifies in-profile
         marking. Value of 'out' specifies out-profile marking. Value of 'none'
         specifies the profile marking of the packet will be inherited from the
         existing enqueuing priority derived from earlier matches in the
         classification hierarchy."
    SYNTAX      INTEGER {
        in     (1),
        out    (2),
        exceed (4),
        inplus (5)
    }

TEgressProfileOrNone             ::= TEXTUAL-CONVENTION
    STATUS      current
    DESCRIPTION
        "The profile marking of a packet. Value of 'in' specifies in-profile
         marking. Value of 'out' specifies out-profile marking. Value of 'de'
         specifies that the profile marking of the packet will be based on the
         DE (Drop-Eligible) bit of the packet. DE bit value of '0' specifies
         in-profile and DE bit value of '1' specifies out-profile marking.

         Value of 'none' specifies the profile marking of the packet will be
         inherited from the existing enqueuing priority derived from earlier
         matches in the classification hierarchy."
    SYNTAX      INTEGER {
        none   (0),
        in     (1),
        out    (2),
        de     (3),
        exceed (4),
        inplus (5)
    }

TAdaptationRule                  ::= TEXTUAL-CONVENTION
    STATUS      current
    DESCRIPTION
        "The adaptation rule to be applied to calculate the operational values
         for the specified entity."
    SYNTAX      INTEGER {
        max     (1),
        min     (2),
        closest (3)
    }

TAdaptationRuleOverride          ::= TEXTUAL-CONVENTION
    STATUS      current
    DESCRIPTION
        "The adaptation rule to be applied to calculate the operational values
         for the specified entity."
    SYNTAX      INTEGER {
        noOverride (0),
        max        (1),
        min        (2),
        closest    (3)
    }

TRemarkType                      ::= TEXTUAL-CONVENTION
    STATUS      current
    DESCRIPTION
        "The remarking to be used."
    SYNTAX      INTEGER {
        none       (1),
        dscp       (2),
        precedence (3)
    }

TIngClassRemarkType              ::= TEXTUAL-CONVENTION
    STATUS      current
    DESCRIPTION
        "The remarking to be used."
    SYNTAX      INTEGER {
        any      (1),
        dot1pExp (2)
    }

TPrecValue                       ::= TEXTUAL-CONVENTION
    STATUS      current
    DESCRIPTION
        "The precedence bits as used in the IPv4 header. This constitutes of 3
         bits and hence can hold the values from 0 to 7."
    SYNTAX      Integer32 (0..7)

TPrecValueOrNone                 ::= TEXTUAL-CONVENTION
    STATUS      current
    DESCRIPTION
        "The precedence bits as used in the IPv4 header. This constitutes of 3
         bits and hence can hold the values from 0 to 7. The value '-1'
         specifies that the precedence value is undefined/unused."
    SYNTAX      Integer32 (-1 | 0..7)

TCpmFilterBurstSize              ::= TEXTUAL-CONVENTION
    STATUS      current
    DESCRIPTION
        "The amount of buffer space (in kbytes) assigned to a queue. The value
         -1 means that the actual value is derived from the corresponding
         buffer policy's default value."
    SYNTAX      Integer32 (-1 | 0..131072)

TBurstSize                       ::= TEXTUAL-CONVENTION
    STATUS      current
    DESCRIPTION
        "The amount of buffer space (in kbytes) assigned to a queue. The value
         -1 means that the actual value is derived from the corresponding
         buffer policy's default value."
    SYNTAX      Integer32 (-1 | 0..1048576)

TBurstSizeOverride               ::= TEXTUAL-CONVENTION
    STATUS      current
    DESCRIPTION
        "The amount of buffer space (in kbytes) assigned to a queue. The value
         -1 means that the actual value is derived from the corresponding
         buffer policy's default value. A value of -2 specifies no override."
    SYNTAX      Integer32 (-2 | -1 | 0..1048576)

TBurstSizeBytesOvr               ::= TEXTUAL-CONVENTION
    STATUS      current
    DESCRIPTION
        "The amount of buffer space (in bytes) assigned to a queue. The value
         -1 means that the actual value is derived from the corresponding
         buffer policy's default value. A value of -2 specifies no override."
    SYNTAX      Integer32 (-2 | -1 | 0..1073741824)

TBurstPercent                    ::= TEXTUAL-CONVENTION
    STATUS      current
    DESCRIPTION
        "The percentage of buffer space assigned to a queue that is reserved
         for some purpose."
    SYNTAX      Integer32 (0..100)

TBurstHundredthsOfPercent        ::= TEXTUAL-CONVENTION
    STATUS      current
    DESCRIPTION
        "The percentage of buffer space assigned to a queue that is reserved
         for some purpose, defined to two decimal places."
    SYNTAX      Integer32 (0..10000)

TBurstPercentOrDefault           ::= TEXTUAL-CONVENTION
    STATUS      current
    DESCRIPTION
        "The percentage of buffer space assigned to a queue that is reserved
         for some purpose. The value -1 means that the actual value is derived
         from the corresponding buffer policy's default value."
    SYNTAX      Integer32 (-1 | 0..100)

TBurstPercentOrDefaultOverride   ::= TEXTUAL-CONVENTION
    STATUS      current
    DESCRIPTION
        "The percentage of buffer space assigned to a queue that is reserved
         for some purpose.

         The value -1 means that the actual value is derived from the
         corresponding buffer policy's default value.

         A value of -2 specifies no override."
    SYNTAX      Integer32 (-2 | -1 | 0..100)

TRatePercent                     ::= TEXTUAL-CONVENTION
    STATUS      current
    DESCRIPTION
        "The percentage of maximum rate allowed."
    SYNTAX      Integer32 (0..100)

TPIRRatePercent                  ::= TEXTUAL-CONVENTION
    STATUS      current
    DESCRIPTION
        "The percentage of maximum PIR rate allowed. A value of 0 is not
         acceptable, so the range begins at 1."
    SYNTAX      Integer32 (1..100)

TLevel                           ::= TEXTUAL-CONVENTION
    STATUS      current
    DESCRIPTION
        "The level of the specified entity while feeding into the parent."
    SYNTAX      Integer32 (1..8)

TPortSchedLevel                  ::= TEXTUAL-CONVENTION
    STATUS      current
    DESCRIPTION
        "The priority level for the specified port scheduler entity."
    SYNTAX      Integer32 (1..8)

TLevelOrDefault                  ::= TEXTUAL-CONVENTION
    STATUS      current
    DESCRIPTION
        "The level of the specified entity while feeding into the parent. The
         value 0 is used to denote a default value."
    SYNTAX      Integer32 (0 | 1..8)

TQueueMode                       ::= TEXTUAL-CONVENTION
    STATUS      current
    DESCRIPTION
        "The mode in which the queue is operating.

         If the queue is operating in the 'priority' mode, it is capable of
         handling traffic differently with two distinct priorities. These
         priorities are assigned by the stages preceding the queueing framework
         in the system.

         When the queue is operating in the 'profile' mode, in other words the
         color aware mode, the queue tries to provide the appropriate bandwidth
         to the packets with different profiles.

         The profiles are assigned according to the configuration of the
         forwarding class or the sub-forwarding class.

         In 'priority' mode, the queue does not have the functionality to
         support the profiled traffic and in such cases the queue will have a
         degraded performance. However, the converse is not valid and a queue
         in 'profile' mode should be capable of supporting the different
         priorities of traffic."
    SYNTAX      INTEGER {
        priority (1),
        profile  (2)
    }

TQueueStatModeFormat             ::= TEXTUAL-CONVENTION
    STATUS      current
    DESCRIPTION
        "The mode in which the queue stats are collected.

         In 'priority' mode separate stats are collected for high and low
         priority packets/octets.

         In 'profile' mode separate stats are collected for in profile and out
         of profile packets/octets.

         In 'v4V6' mode separate stats are collected for IPv4 and IPv6
         packets/octets"
    SYNTAX      INTEGER {
        priority (1),
        profile  (2),
        v4V6     (3)
    }

TEntryIndicator                  ::= TEXTUAL-CONVENTION
    STATUS      current
    DESCRIPTION
        "Uniquely identifies an entry in a policy or filter table. The value 0
         is not a valid entry-id. When used as insertion point the value 0
         indicates that entries must be inserted at the very beginning,
         i.e.before the first entry defined."
    SYNTAX      Unsigned32 (0..65535)

TEntryId                         ::= TEXTUAL-CONVENTION
    STATUS      current
    DESCRIPTION
        "uniquely identifies an entry in a policy or filter table.
         to facilitate insertion of entries in the tables, we recommend
         assigning entry IDs by 10s:  10, 20, 30, etc. "
    SYNTAX      TEntryIndicator (1..65535)

TMatchCriteria                   ::= TEXTUAL-CONVENTION
    STATUS      current
    DESCRIPTION
        "determines whether the entry matches traffic using IP match entries or
         MAC match entries."
    SYNTAX      INTEGER {
        ip   (1),
        mac  (2),
        none (3)
    }

TmnxMdaQos                       ::= TEXTUAL-CONVENTION
    STATUS      current
    DESCRIPTION
        "TmnxMdaQos is an enumerated integer whose value specifies the Quality
         of Service support of a Media Dependent Adapter (MDA)."
    SYNTAX      INTEGER {
        unknown       (0),
        mda           (1),
        hsmda1        (2),
        hsmda2        (3),
        hs            (4),
        fpHwAggShaper (5)
    }

TAtmTdpDescrType                 ::= TEXTUAL-CONVENTION
    STATUS      current
    DESCRIPTION
        "The TAtmTdpDescrType is an enumerated integer whose value indicates
         the types of cell loss priority to be used in conjunction with traffic
         parameters.

         The following values are outlined:
          Integer Value               Interpretation
          -------------               ------------------------
          clp0And1pcr                 PCR applies to CLP 0 and
                                      CLP 1 cell flows
          clp0And1pcrPlusClp0And1scr  PCR applies to CLP 0 and
                                      CLP 1 cell flows.
                                      SCR applies to CLP 0 and
                                      CLP 1 cell flows.
          clp0And1pcrPlusClp0scr      PCR applies to CLP 0 and
                                      CLP 1 cell flows.
                                      SCR applies to CLP 0 cell flows.
          clp0And1pcrPlusClp0scrTag   PCR applies to CLP 0 and
                                      CLP 1 cell flows.
                                      SCR applies to CLP 0 cell flows. "
    SYNTAX      INTEGER {
        clp0And1pcr                (0),
        clp0And1pcrPlusClp0And1scr (1),
        clp0And1pcrPlusClp0scr     (2),
        clp0And1pcrPlusClp0scrTag  (3)
    }

TDEValue                         ::= TEXTUAL-CONVENTION
    STATUS      current
    DESCRIPTION
        "This textual convention specifies the DE (Drop Eligible) bit value.
         The value of '-1' means DE value is not specified."
    SYNTAX      Integer32 (-1 | 0..1)

TQGroupType                      ::= TEXTUAL-CONVENTION
    STATUS      current
    DESCRIPTION
        "This textual convention specifies the type of the Queue-Group."
    SYNTAX      INTEGER {
        port (0),
        vpls (1)
    }

TQosOverrideType                 ::= TEXTUAL-CONVENTION
    STATUS      current
    DESCRIPTION
        "This textual convention specifies the type of the Qos Override."
    SYNTAX      INTEGER {
        queue           (1),
        policer         (2),
        aggRateLimit    (3),
        arbiter         (4),
        scheduler       (5),
        slaAggRateLimit (6),
        wrrGroup        (7)
    }

TQosOverrideTypeId               ::= TEXTUAL-CONVENTION
    STATUS      current
    DESCRIPTION
        "This textual convention indicates the identifier of the queue or
         policer that is overridden, or zero if the item that is overridden is
         not a queue or a policer."
    SYNTAX      Integer32 (0..63)

TmnxIPsecTunnelTemplateId        ::= TEXTUAL-CONVENTION
    STATUS      current
    DESCRIPTION
        "A number used to identify an entry in the tIPsecTnlTempTable."
    SYNTAX      Unsigned32 (1..2048)

TmnxIPsecTunnelTemplateIdOrZero  ::= TEXTUAL-CONVENTION
    STATUS      current
    DESCRIPTION
        "A number used to identify an entry in the tIPsecTnlTempTable or zero."
    SYNTAX      Unsigned32 (0..2048)

TmnxIpSecIsaOperFlags            ::= TEXTUAL-CONVENTION
    STATUS      current
    DESCRIPTION
        "The value of TmnxIpSecIsaOperFlags specifies the operational flags
         that determine the status of the MDAs associated with IPsec ISA."
    SYNTAX      BITS {
        adminDown   (0),
        noActive    (1),
        noResources (2),
        mcAdminDown (3)
    }

TmnxIkePolicyAuthMethod          ::= TEXTUAL-CONVENTION
    STATUS      current
    DESCRIPTION
        "TmnxIkePolicyAuthMethod data type is an enumerated integer that
         describes the type of authentication method used."
    SYNTAX      INTEGER {
        psk             (1),
        hybridX509XAuth (2),
        plainX509XAuth  (3),
        plainPskXAuth   (4),
        cert            (5),
        pskRadius       (6),
        certRadius      (7),
        eap             (8),
        autoEapRadius   (9),
        autoEap         (10)
    }

TmnxIkePolicyAutoEapMethod       ::= TEXTUAL-CONVENTION
    STATUS      current
    DESCRIPTION
        "TmnxIkePolicyAutoEapMethod data type is an enumerated integer that
         describes the type of fallback authentication method use in
         conjunction with the automatic EAP authentication method."
    SYNTAX      INTEGER {
        psk       (1),
        cert      (2),
        pskOrCert (3)
    }

TmnxIkePolicyAutoEapOwnMethod    ::= TEXTUAL-CONVENTION
    STATUS      current
    DESCRIPTION
        "TmnxIkePolicyAutoEapOwnMethod data type is an enumerated integer that
         describes the type of fallback authentication method use in
         conjunction with the automatic EAP authentication method on its own
         side."
    SYNTAX      INTEGER {
        psk  (1),
        cert (2)
    }

TmnxIkePolicyOwnAuthMethod       ::= TEXTUAL-CONVENTION
    STATUS      current
    DESCRIPTION
        "TmnxIkePolicyOwnAuthMethod data type is an enumerated integer that
         describes the type of authentication method used for its own side."
    SYNTAX      INTEGER {
        symmetric (0),
        psk       (1),
        cert      (5),
        eapOnly   (8)
    }

TmnxRsvpDSTEClassType            ::= TEXTUAL-CONVENTION
    STATUS      current
    DESCRIPTION
        "TmnxRsvpDSTEClassType is an unsigned integer in the range of (0..7)
         that defines the class type (CT)."
    SYNTAX      Unsigned32 (0..7)

TmnxAccPlcyQICounters            ::= TEXTUAL-CONVENTION
    STATUS      current
    DESCRIPTION
        "This data type describes a set ingress counters for which accounting
         data can be collected associated with a given queue."
    SYNTAX      BITS {
        hpo (0),
        lpo (1),
        ucp (2),
        hoo (3),
        loo (4),
        uco (5),
        apo (6),
        aoo (7),
        hpd (8),
        lpd (9),
        hod (10),
        lod (11),
        ipf (12),
        opf (13),
        iof (14),
        oof (15)
    }

TmnxAccPlcyQECounters            ::= TEXTUAL-CONVENTION
    STATUS      current
    DESCRIPTION
        "This data type describes a set egress counters for which accounting
         data can be collected associated with a given queue."
    SYNTAX      BITS {
        ipf (0),
        ipd (1),
        opf (2),
        opd (3),
        iof (4),
        iod (5),
        oof (6),
        ood (7)
    }

TmnxAccPlcyPolicerICounters      ::= TEXTUAL-CONVENTION
    STATUS      current
    DESCRIPTION
        "This data type describes a set of ingress counters for which
         accounting data can be collected associated with a given policer.

         ipo : In-profile Packets Offered
         ipd : In-profile Packets Discarded
         opo : Out-profile Packets Offered
         opd : Out-profile Packets Discarded
         ioo : In-profile Octets Offered
         iod : In-profile Octets Discarded
         ooo : Out-profile Octets Offered
         ood : Out-profile Octets Discarded
         ucp : Uncoloured Packets Offered
         uco : Uncoloured Octets Offered
         ipf : In-profile Packets Forwarded
         iof : In-profile Octets Forwarded
         opf : Out-profile Packets Forwarded
         oof : Out-profile Octets Forwarded."
    SYNTAX      BITS {
        ipo (0),
        ipd (1),
        opo (2),
        opd (3),
        ioo (4),
        iod (5),
        ooo (6),
        ood (7),
        ucp (8),
        uco (9),
        ipf (10),
        iof (11),
        opf (12),
        oof (13)
    }

TmnxAccPlcyPolicerECounters      ::= TEXTUAL-CONVENTION
    STATUS      current
    DESCRIPTION
        "This data type describes a set of egress counters for which accounting
         data can be collected associated with a given policer.

          ipo  : In-profile Packets Offered
          ipd  : In-profile Packets Discarded
          opo  : Out-profile Packets Offered
          opd  : Out-profile Packets Discarded
          ioo  : In-profile Octets Offered
          iod  : In-profile Octets Discarded
          ooo  : Out-profile Octets Offered
          ood  : Out-profile Octets Discarded
          ucp  : Uncoloured Packets Offered
          uco  : Uncoloured Octets Offered
          ipf  : In-profile Packets Forwarded
          iof  : In-profile Octets Forwarded
          opf  : Out-Profile Packets Forwarded
          oof  : Out-Profile Octets Forwarded
          xpo  : Exceed-profile Packets Offered;
          xpd  : Exceed-profile Packets Discarded;
          xpf  : Exceed-profile Packets Forwarded;
          xoo  : Exceed-profile Octets Offered;
          xod  : Exceed-profile Octets Discarded;
          xof  : Exceed-profile Octets Forwarded;
          ppo  : In-plus-profile Packets Offered;
          ppd  : In-plus-profile Packets Discarded;
          ppf  : In-plus-profile Packets Forwarded;
          poo  : In-plus-profile Octets Offered;
          pod  : In-plus-profile Octets Discarded;
          pof  : In-plus-profile Octets Forwarded;"
    SYNTAX      BITS {
        ipo (0),
        ipd (1),
        opo (2),
        opd (3),
        ioo (4),
        iod (5),
        ooo (6),
        ood (7),
        ucp (8),
        uco (9),
        ipf (10),
        iof (11),
        opf (12),
        oof (13),
        xpo (14),
        xpd (15),
        xpf (16),
        xoo (17),
        xod (18),
        xof (19),
        ppo (20),
        ppd (21),
        ppf (22),
        poo (23),
        pod (24),
        pof (25)
    }

TmnxAccPlcyOICounters            ::= TEXTUAL-CONVENTION
    STATUS      current
    DESCRIPTION
        "This data type describes a set ingress counters for which accounting
         data can be collected associated with a given counter."
    SYNTAX      BITS {
        apo (0),
        aoo (1),
        hpd (2),
        lpd (3),
        hod (4),
        lod (5),
        ipf (6),
        opf (7),
        iof (8),
        oof (9)
    }

TmnxAccPlcyOECounters            ::= TEXTUAL-CONVENTION
    STATUS      current
    DESCRIPTION
        "This data type describes a set egress counters for which accounting
         data can be collected associated with a given counter."
    SYNTAX      BITS {
        ipf (0),
        ipd (1),
        opf (2),
        opd (3),
        iof (4),
        iod (5),
        oof (6),
        ood (7)
    }

TmnxAccPlcyAACounters            ::= TEXTUAL-CONVENTION
    STATUS      current
    DESCRIPTION
        "This data type describes a set of AA (Application Assurance) counters
         for which accounting data can be collected.

         The bits are defined as follows:
               any (0)  -  enables reporting when there is a change
                           to any counter
               sfa (1)  -  allowed flows from sub
               nfa (2)  -  allowed flows to sub
               sfd (3)  -  denied flows from sub
               nfd (4)  -  denied flows to sub
               saf (5)  -  active flows from sub
               naf (6)  -  active flows to sub
               spa (7)  -  total packets from sub
               npa (8)  -  total packets to sub
               sba (9)  -  total bytes from sub
               nba (10) -  total bytes to sub
               spd (11) -  total discard packets from sub
               npd (12) -  total discard packets to sub
               sbd (13) -  total discard bytes from sub
               nbd (14) -  total discard bytes to sub
               sdf (15) -  short  duration flows
               mdf (16) -  medium duration flows
               ldf (17) -  long   duration flows
               tfd (18) -  total flow duration
               tfc (19) -  total flows completed
               sbm (20) -  max throughput in bytes from sub
               spm (21) -  max throughput in packets from sub
               smt (22) -  max throughput timestamp from sub
               nbm (23) -  max throughput in bytes to sub
               npm (24) -  max throughput in packets to sub
               nmt (25) -  max throughput timestamp to sub
               sfc (26) -  forwarding class from sub
               nfc (27) -  forwarding class to sub"
    SYNTAX      BITS {
        any (0),
        sfa (1),
        nfa (2),
        sfd (3),
        nfd (4),
        saf (5),
        naf (6),
        spa (7),
        npa (8),
        sba (9),
        nba (10),
        spd (11),
        npd (12),
        sbd (13),
        nbd (14),
        sdf (15),
        mdf (16),
        ldf (17),
        tfd (18),
        tfc (19),
        sbm (20),
        spm (21),
        smt (22),
        nbm (23),
        npm (24),
        nmt (25),
        sfc (26),
        nfc (27)
    }

TmnxAccPlcyAASubAttributes       ::= TEXTUAL-CONVENTION
    STATUS      current
    DESCRIPTION
        "This data type describes a set of AA (Application Assurance)
         subscriber attributes which must be included in accounting data.

         The bits are defined as follows:
              appProfile       (0)  - application profile
              appServiceOption (1)  - application service option"
    SYNTAX      BITS {
        appProfile       (0),
        appServiceOption (1)
    }

TmnxIsaBbGrpId                   ::= TEXTUAL-CONVENTION
    STATUS      current
    DESCRIPTION
        "The TmnxIsaBbGrpId data type contains an identification number for an
         ISA-BB group.

         An ISA-BB group is a set of MDA of type 'isa-bb' that together
         performs a particular function such as NAT (Network Address
         Translation) or IP datagram fragment reassembly.

         The value zero means that no ISA-BB Group is defined."
    SYNTAX      Unsigned32 (0..4)

TmnxIsaScalingProfile            ::= TEXTUAL-CONVENTION
    STATUS      current
    DESCRIPTION
        "TmnxIsaScalingProfile is an enumerated integer that specifies the ISA
         scaling profile.

         The meaning of each profile is explained in the customer
         documentation.

         ISA scaling profiles are only used in a virtual machine
         implementation."
    SYNTAX      INTEGER {
        profile1 (1),
        profile2 (2),
        profile3 (3)
    }

TmnxVdoGrpIdIndex                ::= TEXTUAL-CONVENTION
    STATUS      current
    DESCRIPTION
        "TmnxVdoGrpIdIndex data type describes the id of a
         TIMETRA-VIDEO-MIB::tmnxVdoGrpEntry and is the primary index for the
         table."
    SYNTAX      Unsigned32 (1..4)

TmnxVdoGrpId                     ::= TEXTUAL-CONVENTION
    STATUS      current
    DESCRIPTION
        "TmnxVdoGrpId data type describes the identifier for a video group."
    SYNTAX      Unsigned32 (0..4)

TmnxVdoGrpIdOrInherit            ::= TEXTUAL-CONVENTION
    STATUS      current
    DESCRIPTION
        "The data type describes the identifier for a video group. A value of
         '-1' indicates that identifier will be inherited from another object
         that is usually in another MIB table."
    SYNTAX      Integer32 (-1 | 0..4)

TmnxVdoFccServerMode             ::= TEXTUAL-CONVENTION
    STATUS      current
    DESCRIPTION
        "The TmnxVdoFccServerMode data type is an enumerated integer that
         describes the mode of the Fast Channel Change (FCC) server.

         A value of 'burst' indicates that the FCC server is enabled and will
         send the channel at a nominally faster rate than the channel was
         received based on the
         TIMETRA-MCAST-PATH-MGMT-MIB::tmnxMcPathVdoPlcyFCCBurst setting.

         A value of 'dent' indicates that the FCC server will selectively
         discard frames from the original stream based on the value of
         TIMETRA-MCAST-PATH-MGMT-MIB::tmnxMcPathVdoPlcyFCCDentThd.

         A value of 'hybrid' indicates that the FCC server will use combination
         of 'burst' and 'dent' to send the unicast stream to the client.

         A value of 'none' indicates that FCC server is disabled."
    SYNTAX      INTEGER {
        none   (0),
        burst  (1),
        dent   (2),
        hybrid (3)
    }

TmnxVdoPortNumber                ::= TEXTUAL-CONVENTION
    STATUS      current
    DESCRIPTION
        "The data type describes the port number of an Internet transport layer
         protocol."
    SYNTAX      Unsigned32 (1024..5999 | 6251..65535)

TmnxVdoIfName                    ::= TEXTUAL-CONVENTION
    STATUS      current
    DESCRIPTION
        "The data type describes the name of a video interface. The name of a
         video interface must always start with a letter."
    SYNTAX      TNamedItem

TmnxTimeInSec                    ::= TEXTUAL-CONVENTION
    STATUS      current
    DESCRIPTION
        "The data type TmnxTimeInSec describes the Tariff Time for the Charging
         Data Record (CDR)."
    SYNTAX      Unsigned32 (0..86400)

TmnxReasContextVal               ::= TEXTUAL-CONVENTION
    STATUS      current
    DESCRIPTION
        "The value of the label used to identify the entity using the specified
         context value on a specific port.

         31                                   0
         +--------+--------+--------+--------+
         |00000000 00000000 00000000 000XXXXX|
         +--------+--------+--------+--------+

         The value of this object is encoded in the least significant 5 bits
         and represents the context value."
    SYNTAX      Unsigned32 (0..31)

TmnxVdoStatInt                   ::= TEXTUAL-CONVENTION
    STATUS      current
    DESCRIPTION
        "The data type TmnxVdoStatInt is an enumerated integer that specifies
         the time duration for which the video statistics are being counted.
         Setting a variable of this type to 'current' causes the time duration
         to be set to one second which is the least allowed value. A value of
         'interval' makes it necessary for some other MIB object to actually
         quantify the time interval."
    SYNTAX      INTEGER {
        current  (1),
        interval (2)
    }

TmnxVdoOutputFormat              ::= TEXTUAL-CONVENTION
    STATUS      current
    DESCRIPTION
        "The data type TmnxVdoOutputFormat is an enumerated integer that
         specifies the output format of the video stream. Setting a variable of
         this type to 'udp' causes the video stream to be of type 'udp' whereas
         setting a value of 'rtp-udp' causes the video stream to be of type
         'rtp-udp'."
    SYNTAX      INTEGER {
        udp     (1),
        rtp-udp (2)
    }

TmnxVdoAnalyzerAlarm             ::= TEXTUAL-CONVENTION
    STATUS      current
    DESCRIPTION
        "The data type TmnxVdoAnalyzerAlarm is an enumerated integer that
         specifies the severity of the analyzer state alarm. Setting a variable
         of this type to 'none' indicates no error level. A value of 'tnc'
         indicates a TNC (Tech Non-Conformance) error level.A value of 'qos'
         indicates a QOS (Quality of Service) error level. A value of 'poa'
         indicates a POA (Program off Air) error level."
    SYNTAX      INTEGER {
        none (0),
        tnc  (1),
        qos  (2),
        poa  (3)
    }

TmnxVdoAnalyzerAlarmStates       ::= TEXTUAL-CONVENTION
    STATUS      current
    DESCRIPTION
        "The data type TmnxVdoAnalyzerAlarmStates is an octet string that
         represents the analyzer state for the past 10 seconds. Setting a
         variable of this type to 'good'(00) indicates either there was no
         alarm during that second or the state of the stream has been cleared
         from a prior errored state. A value of 'tnc'(01)indicates a TNC (Tech
         Non-Conformance) error occurred during that second. A value of
         'qos'(02) indicates a QOS (Quality of Service) error occurred during
         that second. A value of 'poa'(03) indicates a POA (Program off Air)
         error occurred during that second.

         Since the octet string is 10 bytes long, the 10th byte indicates
         the most recent state of the stream. Below is how an example stream
         would appear. Each byte in the stream holds an alarm state for a
         second.
         good (00),  --  stream was good during 1st second
         tnc  (01),  --  stream had tnc error during 2nd second
         qos  (02),  --  stream had qos error during 3rd second
         qos  (02),  --  stream had qos error during 4th second
         qos  (02),  --  stream had qos error during 5th second
         good (00),  --  stream error was cleared during 6th second
         good (00),  --  stream was good during 7th second
         tnc  (01),  --  stream had tnc error during 8th second
         poa  (03),  --  stream had poa error during 9th second
         good (00)   --  stream error was cleared during 10th second."
    SYNTAX      OCTET STRING (SIZE (10))

TmnxMcPathVdoStSeBufferTime      ::= TEXTUAL-CONVENTION
    STATUS      current
    DESCRIPTION
        "The TmnxMcPathVdoStSeBufferTime data type describes the buffer time
         for the stream-selection."
    SYNTAX      INTEGER {
        buf100ms  (1),
        buf200ms  (2),
        buf300ms  (3),
        buf400ms  (4),
        buf500ms  (5),
        buf600ms  (6),
        buf700ms  (7),
        buf800ms  (8),
        buf900ms  (9),
        buf1000ms (10),
        buf1100ms (11),
        buf1200ms (12),
        buf1300ms (13),
        buf1400ms (14),
        buf1500ms (15),
        buf1600ms (16),
        buf1700ms (17),
        buf1800ms (18),
        buf1900ms (19),
        buf2000ms (20),
        buf2100ms (21),
        buf2200ms (22),
        buf2300ms (23),
        buf2400ms (24),
        buf2500ms (25),
        buf2600ms (26),
        buf2700ms (27),
        buf2800ms (28),
        buf2900ms (29),
        buf3000ms (30)
    }

TmnxMcPathVdoStSeBufferTimeOrZero ::= TEXTUAL-CONVENTION
    STATUS      current
    DESCRIPTION
        "The TmnxMcPathVdoStSeBufferTimeOrZero data type describes the buffer
         time for the stream-selection."
    SYNTAX      INTEGER {
        none      (0),
        buf100ms  (1),
        buf200ms  (2),
        buf300ms  (3),
        buf400ms  (4),
        buf500ms  (5),
        buf600ms  (6),
        buf700ms  (7),
        buf800ms  (8),
        buf900ms  (9),
        buf1000ms (10),
        buf1100ms (11),
        buf1200ms (12),
        buf1300ms (13),
        buf1400ms (14),
        buf1500ms (15),
        buf1600ms (16),
        buf1700ms (17),
        buf1800ms (18),
        buf1900ms (19),
        buf2000ms (20),
        buf2100ms (21),
        buf2200ms (22),
        buf2300ms (23),
        buf2400ms (24),
        buf2500ms (25),
        buf2600ms (26),
        buf2700ms (27),
        buf2800ms (28),
        buf2900ms (29),
        buf3000ms (30)
    }

SvcISID                          ::= TEXTUAL-CONVENTION
    STATUS      current
    DESCRIPTION
        "The SvcISID specifies a 24 bit (0..16777215) service instance
         identifier for the service. As part of the Provider Backbone Bridging
         frames, it is used at the destination PE as a demultiplexor field.

         The value of -1 is used to indicate the value of this object is
         unspecified."
    SYNTAX      Integer32 (-1 | 0..16777215)

TmnxISID                         ::= TEXTUAL-CONVENTION
    STATUS      current
    DESCRIPTION
        "The TmnxISID specifies a 24 bit (1..16777215) service instance
         identifier for the service. As part of the Shortest Path Bridging
         (SPB) frames, it is used at the destination PE as a demultiplexor
         field.

         The value of 0 is used to indicate the value of this object is
         unspecified."
    SYNTAX      Integer32 (0 | 1..16777215)

TIngPolicerId                    ::= TEXTUAL-CONVENTION
    STATUS      current
    DESCRIPTION
        "The data type describes the QoS control policer identifier on ingress
         side."
    SYNTAX      Integer32 (1..32)

TNetIngPolicerId                 ::= TEXTUAL-CONVENTION
    STATUS      current
    DESCRIPTION
        "The data type describes the QoS control policer identifier on network
         ingress side."
    SYNTAX      Integer32 (1..16)

TNetIngPolicerIdOrNone           ::= TEXTUAL-CONVENTION
    STATUS      current
    DESCRIPTION
        "The data type describes the QoS control policer identifier on network
         ingress side or zero when not specified."
    SYNTAX      Integer32 (0 | 1..16)

TIngPolicerIdOrNone              ::= TEXTUAL-CONVENTION
    STATUS      current
    DESCRIPTION
        "The data type describes the QoS control policer identifier on ingress
         side or zero when not specified."
    SYNTAX      Integer32 (0 | 1..32)

TIngressPolicerId                ::= TEXTUAL-CONVENTION
    STATUS      current
    DESCRIPTION
        "The data type describes the QoS control policer identifier on ingress
         side."
    SYNTAX      Integer32 (1..63)

TIngressPolicerIdOrNone          ::= TEXTUAL-CONVENTION
    STATUS      current
    DESCRIPTION
        "The data type describes the QoS control policer identifier on ingress
         side or zero when not specified."
    SYNTAX      Integer32 (0 | 1..63)

TIngDynPolicerIdOrNone           ::= TEXTUAL-CONVENTION
    STATUS      current
    DESCRIPTION
        "The data type describes the QoS dynamic policer identifier on ingress
         side or zero when not specified."
    SYNTAX      Integer32 (0 | 1..63)

TEgrPolicerId                    ::= TEXTUAL-CONVENTION
    STATUS      current
    DESCRIPTION
        "The data type describes the QoS control policer identifier on egress
         side."
    SYNTAX      Integer32 (1..8)

TEgrPolicerIdOrNone              ::= TEXTUAL-CONVENTION
    STATUS      current
    DESCRIPTION
        "The data type describes the QoS control policer identifier on egress
         side or zero when not specified."
    SYNTAX      Integer32 (0 | 1..8)

TEgressPolicerId                 ::= TEXTUAL-CONVENTION
    STATUS      current
    DESCRIPTION
        "The data type describes the QoS control policer identifier on egress
         side."
    SYNTAX      Integer32 (1..63)

TEgressPolicerIdOrNone           ::= TEXTUAL-CONVENTION
    STATUS      current
    DESCRIPTION
        "The data type describes the QoS control policer identifier on egress
         side or zero when not specified."
    SYNTAX      Integer32 (0 | 1..63)

TEgrDynPolicerIdOrNone           ::= TEXTUAL-CONVENTION
    STATUS      current
    DESCRIPTION
        "The data type describes the QoS dynamic policer identifier on egress
         side or zero when not specified."
    SYNTAX      Integer32 (0 | 1..63)

TEgrDynQueueIdOrNone             ::= TEXTUAL-CONVENTION
    STATUS      current
    DESCRIPTION
        "The data type describes the QoS dynamic queue identifier on egress
         side or zero when not specified."
    SYNTAX      Integer32 (0 | 1..63)

TFIRRate                         ::= TEXTUAL-CONVENTION
    STATUS      current
    DESCRIPTION
        "The static fair rate to be used in kbps. The value -1 means maximum
         rate."
    SYNTAX      Integer32 (-1 | 1..100000000)

TBurstSizeBytes                  ::= TEXTUAL-CONVENTION
    STATUS      current
    DESCRIPTION
        "The amount of buffer space (in bytes) assigned to a queue. The value
         -1 means that the actual value is derived from the corresponding
         buffer policy's default value."
    SYNTAX      Integer32 (-1 | 0..1073741824)

THSMDABurstSizeBytes             ::= TEXTUAL-CONVENTION
    STATUS      current
    DESCRIPTION
        "The amount of buffer space (in bytes) assigned to a HSMDA queue. The
         value -1 means that the actual value is derived from the corresponding
         buffer policy's default value."
    SYNTAX      Integer32 (-1 | 0..2688000)

THSMDAQueueBurstLimit            ::= TEXTUAL-CONVENTION
    STATUS      current
    DESCRIPTION
        "An explicit shaping burst size of a HSMDA queue. The value -1 means
         that the actual value is derived from the corresponding queue's
         default value."
    SYNTAX      Integer32 (-1 | 1..1000000)

TClassBurstLimit                 ::= TEXTUAL-CONVENTION
    STATUS      current
    DESCRIPTION
        "An explicit shaping burst size for a class. The value -1 means that
         the actual value is derived from the corresponding class's default
         value."
    SYNTAX      Integer32 (-1 | 1..327680)

TNetIngPlcrBurstSizeBytes        ::= TEXTUAL-CONVENTION
    STATUS      current
    DESCRIPTION
        "The amount of buffer space (in bytes) assigned to a queue by policer.
         The value -1 means that the actual value is derived from the
         corresponding buffer policy's default value."
    SYNTAX      Integer32 (-1 | 128..4161536)

TPlcrBurstSizeBytes              ::= TEXTUAL-CONVENTION
    STATUS      current
    DESCRIPTION
        "The amount of buffer space (in bytes) assigned to a queue by policer.
         The value -1 means that the actual value is derived from the
         corresponding buffer policy's default value."
    SYNTAX      Integer32 (-1 | 0..16777216)

TBurstSizeBytesOverride          ::= TEXTUAL-CONVENTION
    STATUS      current
    DESCRIPTION
        "The amount of buffer space (in bytes) assigned to a queue. The value
         -1 means that the actual value is derived from the corresponding
         buffer policy's default value. A value of -2 specifies no override."
    SYNTAX      Integer32 (-2 | -1 | 0..134217728)

TPolicerBurstSizeBytes           ::= TEXTUAL-CONVENTION
    STATUS      current
    DESCRIPTION
        "The amount of buffer space (in bytes) assigned to a queue by policer.
         The value -1 means that the actual value is derived from the
         corresponding buffer policy's default value."
    SYNTAX      Integer32 (-1 | 0..268435456)

THSMDABurstSizeBytesOverride     ::= TEXTUAL-CONVENTION
    STATUS      current
    DESCRIPTION
        "The amount of buffer space (in bytes) assigned to a HSMDA queue. The
         value -1 means that the actual value is derived from the corresponding
         buffer policy's default value. A value of -2 specifies no override."
    SYNTAX      Integer32 (-2 | -1 | 0..2688000)

TPlcrBurstSizeBytesOverride      ::= TEXTUAL-CONVENTION
    STATUS      current
    DESCRIPTION
        "The amount of buffer space (in bytes) assigned to a queue by policer.
         The value -1 means that the actual value is derived from the
         corresponding buffer policy's default value. A value of -2 specifies
         no override."
    SYNTAX      Integer32 (-2 | -1 | 0..16777216)

TPolicerBurstSizeBytesOverride   ::= TEXTUAL-CONVENTION
    STATUS      current
    DESCRIPTION
        "The amount of buffer space (in bytes) assigned to a queue by policer.
         The value -1 means that the actual value is derived from the
         corresponding buffer policy's default value. A value of -2 specifies
         no override."
    SYNTAX      Integer32 (-2 | -1 | 0..268435456)

TmnxBfdSessionProtocols          ::= TEXTUAL-CONVENTION
    STATUS      current
    DESCRIPTION
        "This data type indicates what protocols are using a BFD session."
    SYNTAX      BITS {
        ospfv2      (0),
        pim         (1),
        isis        (2),
        staticRoute (3),
        mcRing      (4),
        rsvp        (5),
        bgp         (6),
        vrrp        (7),
        srrp        (8),
        mcep        (9),
        ldp         (10),
        ipsecTunnel (11),
        ospfv3      (12),
        mcIpsec     (13),
        mcMobile    (14),
        mplsTp      (15),
        lag         (16),
        opergrp     (17),
        vccv        (18),
        rsvpLsp     (19),
        ldpLsp      (20),
        bgpLsp      (21),
        rip         (22),
        ripng       (23),
        mplsLsp     (24),
        reserved25  (25),
        srPolicy    (26),
        treeSid     (27),
        bier        (28),
        pfcp        (29)
    }

TmnxBfdSessOperState             ::= TEXTUAL-CONVENTION
    STATUS      current
    DESCRIPTION
        "The TmnxBfdSessOperState data type is an enumerated integer that
         describes the values used to identify the operational state of a BFD
         session the instance is relying upon for its fast triggering
         mechanism."
    SYNTAX      INTEGER {
        unknown         (1),
        connected       (2),
        broken          (3),
        peerDetectsDown (4),
        notConfigured   (5),
        noResources     (6)
    }

TmnxBfdOnLspSessFecType          ::= TEXTUAL-CONVENTION
    STATUS      current
    DESCRIPTION
        "An object of type TmnxBfdOnLspSessFecType indicates the Forwarding
         Equivalence Class (FEC) type of a Bidirectional Forwarding Detection
         (BFD) session running on an LSP."
    REFERENCE
        "RFC 5884, 'Bidirectional Forwarding Detection (BFD) for MPLS Label
         Switched Paths (LSPs)', Section 3.1, 'BFD for MPLS LSPs: Motivation'."
    SYNTAX      INTEGER {
        rsvp     (1),
        ldp      (2),
        bgp      (3),
        srTe     (4),
        srPolicy (5),
        srv6     (6)
    }

TmnxBfdSessProtocolState         ::= TEXTUAL-CONVENTION
    STATUS      current
    DESCRIPTION
        "The TmnxBfdSessProtocolState data type is an enumerated integer that
         describes the state of the BFD protocol."
    SYNTAX      INTEGER {
        adminDown (0),
        down      (1),
        init      (2),
        up        (3)
    }

TmnxBfdSessOperFlags             ::= TEXTUAL-CONVENTION
    STATUS      current
    DESCRIPTION
        "The value of TmnxBfdSessOperFlags indicates the reasons why a BFD
         session is not up."
    SYNTAX      BITS {
        noProtocols   (0),
        noHeartBeat   (1),
        echoFailed    (2),
        nbrSignalDown (3),
        fwdPlaneReset (4),
        pathDown      (5),
        nbrAdminDown  (6),
        adminClear    (7),
        misConnDefect (8)
    }

TmnxBfdTermination               ::= TEXTUAL-CONVENTION
    STATUS      current
    DESCRIPTION
        "The TmnxBfdTermination data type is an enumerated integer that indicates
         the termination of the BFD session as follows:
            'iom (1)'   - termination on the IOM card main processor,
            'cpm (2)'   - termination on the CPM card main processor,
            'cpmNp (3)' - termination on the CPM card Network Processor,
            'fp(4)'     - termination on the forwarding plane"
    SYNTAX      INTEGER {
        iom   (1),
        cpm   (2),
        cpmNp (3),
        fp    (4)
    }

TmnxIngPolicerStatMode           ::= TEXTUAL-CONVENTION
    STATUS      current
    DESCRIPTION
        "TmnxIngPolicerStatMode specifies the mode of statistics collected by
         this ingress policer."
    SYNTAX      INTEGER {
        noStats                  (0),
        minimal                  (1),
        offeredProfileNoCIR      (2),
        offeredTotalCIR          (3),
        offeredPriorityNoCIR     (4),
        offeredProfileCIR        (5),
        offeredPriorityCIR       (6),
        offeredLimitedProfileCIR (7),
        offeredProfileCappedCIR  (8),
        offeredLimitedCappedCIR  (9)
    }

TmnxSapIngPolicerStatMode        ::= TEXTUAL-CONVENTION
    STATUS      current
    DESCRIPTION
        "TmnxSapIngPolicerStatMode specifies the mode of statistics collected
         by this sap ingress policer."
    SYNTAX      INTEGER {
        noStats                        (0),
        minimal                        (1),
        offeredProfileNoCIR            (2),
        offeredTotalCIR                (3),
        offeredPriorityNoCIR           (4),
        offeredProfileCIR              (5),
        offeredPriorityCIR             (6),
        offeredLimitedProfileCIR       (7),
        offeredProfileCappedCIR        (8),
        offeredLimitedCappedCIR        (9),
        offeredProfileWithDiscards     (10),
        offeredFourProfileWithDiscards (11)
    }

TmnxNetIngPlcyPolicerStatMode    ::= TEXTUAL-CONVENTION
    STATUS      current
    DESCRIPTION
        "TmnxIngPolicerStatMode specifies the mode of statistics collected by
         this network ingress policer."
    SYNTAX      INTEGER {
        noStats                    (0),
        offeredProfileWithDiscards (10)
    }

TmnxIngPolicerStatModeOverride   ::= TEXTUAL-CONVENTION
    STATUS      current
    DESCRIPTION
        "TmnxIngPolicerStatModeOverride specifies the override mode of
         statistics collected by this ingress policer."
    SYNTAX      INTEGER {
        noOverride               (-1),
        noStats                  (0),
        minimal                  (1),
        offeredProfileNoCIR      (2),
        offeredTotalCIR          (3),
        offeredPriorityNoCIR     (4),
        offeredProfileCIR        (5),
        offeredPriorityCIR       (6),
        offeredLimitedProfileCIR (7),
        offeredProfileCappedCIR  (8),
        offeredLimitedCappedCIR  (9)
    }

TmnxEgrPolicerStatMode           ::= TEXTUAL-CONVENTION
    STATUS      current
    DESCRIPTION
        "TmnxEgrPolicerStatMode specifies the mode of statistics collected by
         this egress policer."
    SYNTAX      INTEGER {
        noStats                    (0),
        minimal                    (1),
        offeredProfileNoCIR        (2),
        offeredTotalCIR            (3),
        offeredProfileCIR          (4),
        offeredLimitedCappedCIR    (5),
        offeredProfileCappedCIR    (6),
        offeredTotalCirExceed      (8),
        offeredFourProfileNoCir    (9),
        offeredTotalCirFourProfile (10)
    }

TmnxEgrPolicerStatModeOverride   ::= TEXTUAL-CONVENTION
    STATUS      current
    DESCRIPTION
        "TmnxEgrPolicerStatModeOverride specifies the override mode of
         statistics collected by this egress policer."
    SYNTAX      INTEGER {
        noOverride                 (-1),
        noStats                    (0),
        minimal                    (1),
        offeredProfileNoCIR        (2),
        offeredTotalCIR            (3),
        offeredProfileCIR          (4),
        offeredLimitedCappedCIR    (5),
        offeredProfileCappedCIR    (6),
        offeredTotalCirExceed      (8),
        offeredFourProfileNoCir    (9),
        offeredTotalCirFourProfile (10)
    }

TmnxTlsGroupId                   ::= TEXTUAL-CONVENTION
    STATUS      current
    DESCRIPTION
        "A number used to identify a TLS Group. This ID must be unique within
         that Service Domain."
    SYNTAX      Unsigned32 (1..4094)

TSubHostId                       ::= TEXTUAL-CONVENTION
    STATUS      current
    DESCRIPTION
        "A number used to uniquely identify a subscriber host in the system"
    SYNTAX      Unsigned32

TDirection                       ::= TEXTUAL-CONVENTION
    STATUS      current
    DESCRIPTION
        "TDirection denotes a direction."
    SYNTAX      INTEGER {
        both    (0),
        ingress (1),
        egress  (2)
    }

TDirectionIngEgr                 ::= TEXTUAL-CONVENTION
    STATUS      current
    DESCRIPTION
        "TDirectionIngEgr denotes a direction."
    SYNTAX      INTEGER {
        ingress (1),
        egress  (2)
    }

TBurstLimit                      ::= TEXTUAL-CONVENTION
    STATUS      current
    DESCRIPTION
        "An explicit shaping burst size for a queue. The value of -1 specifies
         system default value."
    SYNTAX      Integer32 (-1 | 1..14000000)

TMacFilterType                   ::= TEXTUAL-CONVENTION
    STATUS      current
    DESCRIPTION
        "A type containing the possible types of MAC filters provided by the
         system"
    SYNTAX      INTEGER {
        normal (1),
        isid   (2),
        vid    (3)
    }

TIPFilterType                    ::= TEXTUAL-CONVENTION
    STATUS      current
    DESCRIPTION
        "A type containing the possible types of IP/IPv6 filters provided by
         the system."
    SYNTAX      INTEGER {
        normal         (1),
        vxlanVni       (2),
        tagged-entries (3)
    }

TmnxPwGlobalId                   ::= TEXTUAL-CONVENTION
    STATUS      current
    DESCRIPTION
        "A number used to identify a global pseudo-wire routing identifier."
    SYNTAX      Unsigned32 (1..4294967295)

TmnxPwGlobalIdOrZero             ::= TEXTUAL-CONVENTION
    STATUS      current
    DESCRIPTION
        "A number used to identify a global pseudo-wire routing identifier or
         zero."
    SYNTAX      Unsigned32

TmnxPwPathHopId                  ::= TEXTUAL-CONVENTION
    STATUS      current
    DESCRIPTION
        "A number used to identify a specific hop associated with pseudo-wire
         routing path."
    SYNTAX      Unsigned32 (1..16)

TmnxPwPathHopIdOrZero            ::= TEXTUAL-CONVENTION
    STATUS      current
    DESCRIPTION
        "A number used to identify a specific hop associated with pseudo-wire
         routing path."
    SYNTAX      Unsigned32 (0..16)

TmnxSpokeSdpId                   ::= TEXTUAL-CONVENTION
    STATUS      current
    DESCRIPTION
        "A number used to identify a multi-segment pseudo-wire provider-edge
         identifier."
    SYNTAX      Unsigned32 (1..4294967295)

TmnxSpokeSdpIdOrZero             ::= TEXTUAL-CONVENTION
    STATUS      current
    DESCRIPTION
        "A number used to identify a multi-segment pseudo-wire provider-edge
         identifier."
    SYNTAX      Unsigned32

TmnxMsPwPeSignaling              ::= TEXTUAL-CONVENTION
    STATUS      current
    DESCRIPTION
        "A number used to identify a multi-segment pseudo-wire provider-edge
         signaling type."
    SYNTAX      INTEGER {
        auto   (1),
        master (2)
    }

TmnxLdpFECType                   ::= TEXTUAL-CONVENTION
    STATUS      current
    DESCRIPTION
        "TmnxLdpFECType determines the kind of FEC that the label mapping,
         withdraw, release and request messages are referring to."
    SYNTAX      INTEGER {
        addrWildcard (1),
        addrPrefix   (2),
        addrHost     (3),
        vll          (128),
        vpws         (129),
        vpls         (130)
    }

TmnxSvcOperGrpCreationOrigin     ::= TEXTUAL-CONVENTION
    STATUS      current
    DESCRIPTION
        "A number used to identify creation origin for the service operational
         group."
    SYNTAX      INTEGER {
        manual    (1),
        mvrp      (2),
        dynScript (7)
    }

TmnxOperGrpHoldUpTime            ::= TEXTUAL-CONVENTION
    STATUS      current
    DESCRIPTION
        "TmnxOperGrpHoldUpTime indicates time-interval in seconds for the
         service operational-group hold uptime."
    SYNTAX      Unsigned32 (0..3600)

TmnxOperGrpHoldDownTime          ::= TEXTUAL-CONVENTION
    STATUS      current
    DESCRIPTION
        "TmnxOperGrpHoldDownTime indicates time-interval in seconds for the
         service operational-group hold down time."
    SYNTAX      Unsigned32 (0..3600)

TmnxSrrpPriorityStep             ::= TEXTUAL-CONVENTION
    STATUS      current
    DESCRIPTION
        "TmnxSrrpPriorityStep indicates the range of the priority steps used by
         the operational group to monitor SRRP."
    SYNTAX      Integer32 (0..10)

TmnxAiiType                      ::= TEXTUAL-CONVENTION
    STATUS      current
    DESCRIPTION
        "TmnxAiiType indicates LDP FEC 129 Attachment Individual Identifier
         (AII) type."
    SYNTAX      INTEGER {
        aiiType1 (1),
        aiiType2 (2)
    }

TmnxSpbFid                       ::= TEXTUAL-CONVENTION
    STATUS      current
    DESCRIPTION
        "TmnxSpbFid indicates Shortest Path Bridging forwarding database
         identifier."
    SYNTAX      Integer32 (1..4095)

TmnxSpbFidOrZero                 ::= TEXTUAL-CONVENTION
    STATUS      current
    DESCRIPTION
        "TmnxSpbFid indicates Shortest Path Bridging forwarding database
         identifier."
    SYNTAX      Integer32 (0..4095)

TmnxSpbBridgePriority            ::= TEXTUAL-CONVENTION
    STATUS      current
    DESCRIPTION
        "TmnxSpbFid indicates the bridge priority for Shortest Path Bridging."
    SYNTAX      Integer32 (0..15)

TmnxSlopeMap                     ::= TEXTUAL-CONVENTION
    STATUS      current
    DESCRIPTION
        "TmnxSlopeMap indicates the mapping style of the slope."
    SYNTAX      INTEGER {
        none    (0),
        low     (1),
        high    (2),
        highLow (3)
    }

TmnxCdrType                      ::= TEXTUAL-CONVENTION
    STATUS      current
    DESCRIPTION
        "The TmnxCdrType is an enumerated integer that describes the current
         charging type in Charging Data Record (CDR).

         pgwCdr - indicates Packet data network Gateway CDR
         gCdr - indicates Gateway GPRS Support Node (GGSN) CDR, where
                   GPRS stands for General Packet Radio Service.
         eGCdr - indicates Enhanced Gateway GPRS Support Node (GGSN) CDR."
    SYNTAX      INTEGER {
        pgwCdr (1),
        gCdr   (2),
        eGCdr  (3)
    }

TmnxThresholdGroupType           ::= TEXTUAL-CONVENTION
    STATUS      current
    DESCRIPTION
        "The TmnxThresholdGroupType is an enumerated integer that describes the
         group type in threshold based monitoring.

         brMgmtLimit - indicates the group for bearer management limit
         brMgmtCfSuccess - indicates the group for bearer management
                           call flow success
         brMgmtCfFailure - indicates the group for bearer management
                           call flow failure
         brMgmtTraffic - indicates the group for bearer management traffic
         pathMgmt - indicates the group for path management
         mgIsmSystem - indicates the group for the system of mobile gateway
                       integrated service module
         pdnConnections - indicates the group for the Packet Data Network (PDN)
                          connections."
    SYNTAX      INTEGER {
        brMgmtLimit     (1),
        brMgmtCfSuccess (2),
        brMgmtCfFailure (3),
        brMgmtTraffic   (4),
        pathMgmt        (5),
        pdnConnections  (6),
        mgIsmSystem     (7)
    }

TmnxVpnIpBackupFamily            ::= TEXTUAL-CONVENTION
    STATUS      current
    DESCRIPTION
        "The value of TmnxVpnIpBackupFamily specifies the respective vpn family
         for which backup paths would be enabled."
    SYNTAX      BITS {
        ipv4 (0),
        ipv6 (1)
    }

TmnxTunnelGroupId                ::= TEXTUAL-CONVENTION
    STATUS      current
    DESCRIPTION
        "The value of TmnxTunnelGroupId specifies the tunnel-group identifier."
    SYNTAX      Unsigned32 (1..64)

TmnxTunnelGroupIdOrZero          ::= TEXTUAL-CONVENTION
    STATUS      current
    DESCRIPTION
        "The value of TmnxTunnelGroupId specifies the tunnel-group identifier
         including zero indicating that group-id is not specified."
    SYNTAX      Unsigned32 (0..64)

TmnxQosBytesHex                  ::= TEXTUAL-CONVENTION
    DISPLAY-HINT "2x "
    STATUS      current
    DESCRIPTION
        "Represents the QoS bytes that has been requested for the bearer
         context of an User Equipment (UE)."
    SYNTAX      OCTET STRING (SIZE (0..30))

TSiteOperStatus                  ::= TEXTUAL-CONVENTION
    STATUS      current
    DESCRIPTION
        "TSiteOperStatus data type is an enumerated integer that describes the
         values used to identify the current operational state of a site."
    SYNTAX      INTEGER {
        up            (1),
        down          (2),
        outOfResource (3)
    }

TmnxSpbFdbLocale                 ::= TEXTUAL-CONVENTION
    STATUS      current
    DESCRIPTION
        "TmnxSpbFdbLocale data type is an enumerated integer that describes the
         values used to indicate source of forwarding database (FDB) entry for
         Shortest Path Bridging (SPB)."
    SYNTAX      INTEGER {
        local   (1),
        sap     (2),
        sdp     (3),
        unknown (4)
    }

TmnxSpbFdbState                  ::= TEXTUAL-CONVENTION
    STATUS      current
    DESCRIPTION
        "TmnxSpbFdbState data type is an enumerated integer that describes the
         values used to indicate state of the forwarding database FDB entry for
         Shortest Path Bridging (SPB)."
    SYNTAX      INTEGER {
        ok            (0),
        addModPending (1),
        delPending    (2),
        sysFdbLimit   (3),
        noFateShared  (4),
        svcFdbLimit   (5),
        noUcast       (6)
    }

TmnxCdrDiagnosticAction          ::= TEXTUAL-CONVENTION
    STATUS      current
    DESCRIPTION
        "The TmnxCdrDiagnosticAction is an enumerated integer that describes
         whether the Diagnostics should be included or excluded in the Charging
         Data Record (CDR)."
    SYNTAX      INTEGER {
        included (1),
        excluded (2)
    }

TmnxLinkMapProfileId             ::= TEXTUAL-CONVENTION
    STATUS      current
    DESCRIPTION
        "The data type TmnxLinkMapProfileId describes the link map profile
         identifier."
    SYNTAX      Integer32 (1..64)

TmnxLinkMapProfileIdOrZero       ::= TEXTUAL-CONVENTION
    STATUS      current
    DESCRIPTION
        "The data type TmnxLinkMapProfileId describes the link map profile
         identifier or zero."
    SYNTAX      Integer32 (0 | 1..64)

TmnxDayOfWeek                    ::= TEXTUAL-CONVENTION
    STATUS      current
    DESCRIPTION
        "The TmnxDayOfWeek is an enumerated integer that describes the day of
         the week."
    SYNTAX      INTEGER {
        unspecified (0),
        sunday      (1),
        monday      (2),
        tuesday     (3),
        wednesday   (4),
        thursday    (5),
        friday      (6),
        saturday    (7)
    }

TmnxDayOfWeekList                ::= TEXTUAL-CONVENTION
    STATUS      current
    DESCRIPTION
        "The TmnxDayOfWeekList describes days of the week in a bitset format."
    SYNTAX      BITS {
        sunday    (0),
        monday    (1),
        tuesday   (2),
        wednesday (3),
        thursday  (4),
        friday    (5),
        saturday  (6)
    }

TmnxMplsTpGlobalID               ::= TEXTUAL-CONVENTION
    STATUS      current
    DESCRIPTION
        "The value of TmnxMplsTpGlobalID specifies the MPLS-TP global
         identifier."
    REFERENCE
        "RFC 6370, 'MPLS Transport Profile (MPLS-TP) Identifiers',
         Section 3, 'Uniquely Identifying an Operator - the Global_ID'."
    SYNTAX      Unsigned32

TmnxMplsTpNodeID                 ::= TEXTUAL-CONVENTION
    STATUS      current
    DESCRIPTION
        "The value of TmnxMplsTpNodeID specifies the MPLS-TP node identifier."
    REFERENCE
        "RFC 6370, 'MPLS Transport Profile (MPLS-TP) Identifiers',
         Section 4, 'Node and Interface Identifiers'."
    SYNTAX      Unsigned32

TmnxMplsTpTunnelType             ::= TEXTUAL-CONVENTION
    STATUS      current
    DESCRIPTION
        "The type of this MPLS-TP tunnel entity."
    SYNTAX      INTEGER {
        mplsTpStatic (1)
    }

TmnxDistCpuProtPacketRateLimit   ::= TEXTUAL-CONVENTION
    STATUS      current
    DESCRIPTION
        "A packet rate limit expressed in packets per second for Distributed
         CPU Protection Policy parameters. The value -1 means max rate."
    SYNTAX      Integer32 (-1 | 0..255)

TmnxDistCpuProtPacketPolicerRateLimit ::= TEXTUAL-CONVENTION
    STATUS      current
    DESCRIPTION
        "A packet rate limit expressed in packets per second for Distributed
         CPU Protection Policy parameters. The value -1 means max rate."
    SYNTAX      Integer32 (-1 | 0..8000)

TmnxDistCpuProtRate              ::= TEXTUAL-CONVENTION
    STATUS      current
    DESCRIPTION
        "A kbps limiting rate in kilobits per second for Distributed CPU
         Protection Policy parameters. The value -1 means max rate."
    SYNTAX      Integer32 (-1 | 1..20000000)

TmnxDistCpuProtBurstSize         ::= TEXTUAL-CONVENTION
    STATUS      current
    DESCRIPTION
        "The amount of buffer space (in kilobytes) assigned to a queue by
         policer for Distributed CPU Protection Policy parameters."
    SYNTAX      Integer32 (-1 | 0..4194304)

TmnxDistCpuProtActionDuration    ::= TEXTUAL-CONVENTION
    STATUS      current
    DESCRIPTION
        "An exceed action rate in seconds for Distributed CPU Protection Policy
         parameters determining hold-down duration for specified exceed-action.
         The value of 0 means no hold-down and value of -1 means indefinite
         hold-down duration."
    SYNTAX      Integer32 (-1 | 0 | 1..10080)

TmnxDistCpuProtAction            ::= TEXTUAL-CONVENTION
    STATUS      current
    DESCRIPTION
        "The TmnxDistCpuProtAction data type is an enumerated integer
         that describes the values used to specify the action to be taken on the
         traffic when the filter entry matches.
         discard      (1)  packets matching the filter entry are discarded
         low-priority (2)  packets matching the filter entry are marked as
                           low-priority
         none         (3)  no action is taken."
    SYNTAX      INTEGER {
        discard      (1),
        low-priority (2),
        none         (3)
    }

TmnxDistCpuProtEnforceType       ::= TEXTUAL-CONVENTION
    STATUS      current
    DESCRIPTION
        "The TmnxDistCpuProtEnforceType data type is an enumerated integer that
         describes the values used to specify the enforcement type."
    SYNTAX      INTEGER {
        static  (1),
        dynamic (2),
        shared  (3)
    }

TmnxDistCpuProtProtocolId        ::= TEXTUAL-CONVENTION
    STATUS      current
    DESCRIPTION
        "The TmnxDistCpuProtProtocolId data type is an enumerated integer that
         indicates the protocols supported for the Distributed CPU Protection
         Policy."
    SYNTAX      INTEGER {
        arp                (1),
        dhcp               (2),
        http-redirect      (3),
        icmp               (4),
        igmp               (5),
        mld                (6),
        ndis               (7),
        pppoe-pppoa        (8),
        all-unspecified    (9),
        mpls-ttl           (10),
        bfd-cpm            (11),
        bgp                (12),
        eth-cfm            (13),
        isis               (14),
        ldp                (15),
        ospf               (16),
        pim                (17),
        rsvp               (18),
        icmp-ping-check    (19),
        lacp               (21),
        vrrp               (22),
        multi-chassis      (23),
        multi-chassis-sync (24),
        ssh                (25),
        radius             (26),
        needsIcmp          (27)
    }

TmnxDistCpuProtDuneProtocolId    ::= TEXTUAL-CONVENTION
    STATUS      current
    DESCRIPTION
        "The TmnxDistCpuProtDuneProtocolId data type is an enumerated integer
         that indicates the protocols supported for the Distributed CPU
         Protection Policy in IXR systems."
    SYNTAX      INTEGER {
        arp             (1),
        dhcp            (2),
        igmp            (5),
        mld             (6),
        all-unspecified (9),
        bgp             (12),
        isis            (14),
        ldp             (15),
        ospf            (16),
        pim             (17),
        rsvp            (18),
        vrrp            (22),
        bfd             (25),
        ftp             (26),
        icmp-v4         (27),
        icmp-v6         (28),
        l3-to-my-ipv4   (29),
        l3-to-my-ipv6   (30),
        lsp-ping        (31),
        mc-lag          (32),
        mcast-snooping  (33),
        radius          (34),
        rip             (35),
        sbfd-reflector  (36),
        snmp            (37),
        ssh             (38),
        stp             (39),
        tacacs          (40),
        telnet          (41),
        tftp            (42),
        twamp           (43)
    }

TmnxDistCpuProtRateType          ::= TEXTUAL-CONVENTION
    STATUS      current
    DESCRIPTION
        "The TmnxDistCpuProtRateType data type is an enumerated integer that
         describes the rate type being applied by the policer for the
         Distributed CPU Protection Policy."
    SYNTAX      INTEGER {
        packets (1),
        kbps    (2)
    }

TmnxDistCpuProtLogEventType      ::= TEXTUAL-CONVENTION
    STATUS      current
    DESCRIPTION
        "The TmnxDistCpuProtLogEventType data type is an enumerated integer
         that describes the state of log events for Distributed CPU Protection
         Policy.
         none         (0)  indicates log events is disabled
         enable       (1)  indicates log events is enabled
         verbose      (2)  indicates generation of additional log events to be
                           used for debug/tuning/investigations which would have
                           not been generated when TmnxDistCpuProtLogEventType
                           is set to 'enable'."
    SYNTAX      INTEGER {
        none    (0),
        enable  (1),
        verbose (2)
    }

TmnxDistCpuProtState             ::= TEXTUAL-CONVENTION
    STATUS      current
    DESCRIPTION
        "The TmnxDistCpuProtState data type is an enumerated integer that
         describes the state of the policer for the Distributed CPU Protection
         Policy."
    SYNTAX      INTEGER {
        exceed         (1),
        conform        (2),
        not-applicable (3)
    }

TmnxIsidMFibStatus               ::= TEXTUAL-CONVENTION
    STATUS      current
    DESCRIPTION
        "The TmnxIsidMFibStatus data type describes the MFIB status of the
         ISID."
    SYNTAX      BITS {
        ok           (0),
        addPending   (1),
        delPending   (2),
        sysMFibLimit (3),
        useDefMCTree (4)
    }

TmnxBfdIntfSessOperState         ::= TEXTUAL-CONVENTION
    STATUS      current
    DESCRIPTION
        "The TmnxBfdIntfSessOperState data type is an enumerated integer that
         describes the values used to identify the operational state of a BFD
         session is relying upon for its fast triggering mechanism."
    SYNTAX      INTEGER {
        unknown         (1),
        connected       (2),
        broken          (3),
        peerDetectsDown (4),
        notConfigured   (5),
        noResources     (6)
    }

TmnxBfdEncap                     ::= TEXTUAL-CONVENTION
    STATUS      current
    DESCRIPTION
        "The TmnxBfdEncap data type is an enumerated integer indicating
         encapsulation used for in the BFD operation."
    SYNTAX      INTEGER {
        ipv4 (1)
    }

TLDisplayString                  ::= TEXTUAL-CONVENTION
    DISPLAY-HINT "255a"
    STATUS      current
    DESCRIPTION
        "The TLDisplayString is DisplayString of 1022 characters.

         Any object defined using this syntax may not exceed 1022 characters in
         length."
    SYNTAX      OCTET STRING (SIZE (0..1022))

IPv6FlowLabel                    ::= TEXTUAL-CONVENTION
    STATUS      current
    DESCRIPTION
        "The flow identifier or Flow Label in an IPv6
         packet header that may be used to discriminate
         traffic flows.  (RFC3595).
         The value -1 indicates 'no flowLabel' "
    SYNTAX      Integer32 (-1 | 0..1048575)

IPv6FlowLabelMask                ::= TEXTUAL-CONVENTION
    STATUS      current
    DESCRIPTION
        "IPv6 flow label mask"
    SYNTAX      Unsigned32 (0..1048575)

TmnxWlanGwIsaGrpId               ::= TEXTUAL-CONVENTION
    STATUS      current
    DESCRIPTION
        "The TmnxWlanGwIsaGrpId data type contains an identification number for
         a Wireless Local Access Network Gateway Integrated Service Adaptor
         group."
    SYNTAX      Unsigned32 (1..4)

TmnxWlanGwIsaGrpIdOrZero         ::= TEXTUAL-CONVENTION
    STATUS      current
    DESCRIPTION
        "The TmnxWlanGwIsaGrpIdOrZero data type contains an identification
         number for a Wireless Local Access Network Gateway Integrated Service
         Adaptor (ISA) group.

         The value zero means that no WLAN Gateway ISA Group is defined."
    SYNTAX      Unsigned32 (0..4)

TmnxMplsLdpNgIdType              ::= TEXTUAL-CONVENTION
    STATUS      current
    DESCRIPTION
        "A value that represents the type of LDP identifier

         ipv4(1)     An IPv4 identifier type as defined by the
                     InetAddressIPv4 textual convention.

         ipv6(2)     An IPv6 identifier type as defined by the
                     InetAddressIPv6 textual convention.

         Each definition of a concrete TmnxMplsLdpNgIdType value must be
         accompanied by a definition of a textual convention for use with that
         TmnxMplsLdpNgIdType.

         Implementations must ensure that TmnxMplsLdpNgIdType objects
         and any dependent objects (e.g., TmnxMplsLdpNgIdentifier objects) are
         consistent.  An inconsistentValue error must be generated
         if an attempt to change an TmnxMplsLdpNgIdType object would,
         for example, lead to an undefined TmnxMplsLdpNgIdentifier value. In
         particular, TmnxMplsLdpNgIdType/TmnxMplsLdpNgIdentifier pairs must be
         changed together if the identifier type changes (e.g., from
         ipv6(2) to ipv4(1))."
    SYNTAX      INTEGER {
        ipv4 (1),
        ipv6 (2)
    }

TmnxMplsLdpNgIdentifier          ::= TEXTUAL-CONVENTION
    STATUS      current
    DESCRIPTION
        "The LDP identifier is a eighteen octet quantity which is used to
         identify a Label Switch Router (LSR) label space.

         When the LDP Id type is 'ipv4', the first four octets encode an IP
         address assigned to the LSR, and next two octets identify a specific
         label space within the LSR assigned to the LSR.

         When the LDP Id type is 'ipv6', the first sixteen octets encode an IP
         address an assigned to the LSR, and last two octets identify a
         specific label space within the LSR."
    SYNTAX      OCTET STRING (SIZE (0..18))

TmnxMplsLsrNgIdentifier          ::= TEXTUAL-CONVENTION
    STATUS      current
    DESCRIPTION
        "The Label Switch Router (LSR) identifier is the first 16 bytes or the
         Router Id component of the IPv6 Label Distribution Protocol (LDP)
         identifier."
    SYNTAX      OCTET STRING (SIZE (16))

TmnxLagPerLinkHashClass          ::= TEXTUAL-CONVENTION
    STATUS      current
    DESCRIPTION
        "The TmnxLagPerLinkHashClass is the class of traffic which along with
         the relative weight is used in the egress hashing on the LAG."
    SYNTAX      Integer32 (1..3)

TmnxLagPerLinkHashClassOrNone    ::= TEXTUAL-CONVENTION
    STATUS      current
    DESCRIPTION
        "The TmnxLagPerLinkHashClass is the class of traffic which along with
         the relative weight is used in the egress hashing on the LAG."
    SYNTAX      Integer32 (0..3)

TmnxLagPerLinkHashWeight         ::= TEXTUAL-CONVENTION
    STATUS      current
    DESCRIPTION
        "The TmnxLagPerLinkHashWeight is the relative weight of the traffic
         which along with the class is used in the egress hashing on the LAG."
    SYNTAX      Integer32 (1..1024)

BgpConnectRetryTime              ::= TEXTUAL-CONVENTION
    STATUS      current
    DESCRIPTION
        "The value of BgpConnectRetryTime is a time interval in seconds for a
         'ConnectRetry' timer.default is 120 seconds."
    REFERENCE
        "BGP4-MIB.bgpPeerConnectRetryInterval"
    SYNTAX      Integer32 (1..65535)

BgpHoldTime                      ::= TEXTUAL-CONVENTION
    STATUS      current
    DESCRIPTION
        "The value of BgpHoldTime is a time interval in seconds for Hold Timer."
    REFERENCE
        "BGP4-MIB.bgpPeerHoldTime"
    SYNTAX      Integer32 (0 | 3..65535)

TmnxInternalSchedWeightMode      ::= TEXTUAL-CONVENTION
    STATUS      current
    DESCRIPTION
        "The value of TmnxInternalSchedWeightMode specifies the weight-mode
         applied to queues using internal-scheduler. Various modes can be
         enumerated as follows:

            noOverride (1)        - follows queue behavior specified at the card
                                    level.
            default (2)           - queues are equally weighted except for
                                    mixed-speed LAG (when the value of
                                    TIMETRA-LAG-MIB.mib::tLagPerFpIngQueuing is
                                    set to 'false (2)') where queues are weighted
                                    based on port-speed.
            forceEqual (3)        - all queues are always equally weighted.
            offeredLoad (4)       - queues are weighted based on offered load.
            cappedOfferedLoad (5) - queues are weighted based on offered load
                                    capped by admin PIR."
    SYNTAX      INTEGER {
        noOverride        (1),
        default           (2),
        forceEqual        (3),
        offeredLoad       (4),
        cappedOfferedLoad (5)
    }

TmnxHigh32                       ::= TEXTUAL-CONVENTION
    STATUS      current
    DESCRIPTION
        "The upper 32 bits of a 64 bit value."
    SYNTAX      Unsigned32

TmnxLow32                        ::= TEXTUAL-CONVENTION
    STATUS      current
    DESCRIPTION
        "The lower 32 bits of a 64 bit value."
    SYNTAX      Unsigned32

TQosQueuePIRRate                 ::= TEXTUAL-CONVENTION
    STATUS      current
    DESCRIPTION
        "The PIR rate to be used in kbps. The value -1 means maximum rate."
    SYNTAX      Integer32 (-1 | 1..2000000000)

TQosQueueCIRRate                 ::= TEXTUAL-CONVENTION
    STATUS      current
    DESCRIPTION
        "The CIR rate to be used in kbps. The value -1 means maximum rate."
    SYNTAX      Integer32 (-1 | 0..2000000000)

TQosQueuePIRRateOverride         ::= TEXTUAL-CONVENTION
    STATUS      current
    DESCRIPTION
        "The PIR rate to be used in kbps. The value -1 means maximum rate. A
         value of -2 specifies no override."
    SYNTAX      Integer32 (-2 | -1 | 1..2000000000)

TQosQueueCIRRateOverride         ::= TEXTUAL-CONVENTION
    STATUS      current
    DESCRIPTION
        "The CIR rate to be used in kbps. The value -1 means maximum rate. A
         value of -2 specifies no override."
    SYNTAX      Integer32 (-2 | -1 | 0..2000000000)

TResolveStatus                   ::= TEXTUAL-CONVENTION
    STATUS      current
    DESCRIPTION
        "The TResolveStatus indicates resolution status of the tunnels."
    SYNTAX      INTEGER {
        disabled        (0),
        filter          (1),
        any             (2),
        match-family-ip (3)
    }

LAGInterfaceNumber               ::= TEXTUAL-CONVENTION
    STATUS      current
    DESCRIPTION
        "The unique number identifying a LAG interface.

         There are maximum 64 LAG interfaces, when the value of
         TIMETRA-CHASSIS-MIB::tmnxChassisType is '5' (ESS-1/SR-1)."
    SYNTAX      Integer32 (1..800)

LAGInterfaceNumberOrZero         ::= TEXTUAL-CONVENTION
    STATUS      current
    DESCRIPTION
        "LAGInterfaceNumberOrZero is similar to LAGInterfaceNumber but includes
         zero indicating invalid LAG identifier."
    SYNTAX      Integer32 (0 | 1..800)

TmnxRouteTargetOrigin            ::= TEXTUAL-CONVENTION
    STATUS      current
    DESCRIPTION
        "TmnxRouteTargetOrigin indicates the origin of the route-target policy."
    SYNTAX      INTEGER {
        none        (0),
        configured  (1),
        derivedVpls (2),
        derivedEvi  (3),
        vsi         (4)
    }

TmnxRouteDistType                ::= TEXTUAL-CONVENTION
    STATUS      current
    DESCRIPTION
        "TmnxRouteDistType indicates the type of the route-distinguisher."
    SYNTAX      INTEGER {
        none        (0),
        configured  (1),
        derivedVpls (2),
        derivedEvi  (3),
        auto        (4),
        default     (5)
    }

TmnxScriptAuthType               ::= TEXTUAL-CONVENTION
    STATUS      current
    DESCRIPTION
        "The tmnxCliScriptAuthUserType datatype is an enumerated integer that
         indicates the type of module executing a CLI command script."
    SYNTAX      INTEGER {
        none                          (0),
        cron                          (1),
        event-script                  (3),
        cron-python                   (5),
        event-script-python           (6),
        subscriber-mgmt-pysros-script (7)
    }

TmnxISIDNoZero                   ::= TEXTUAL-CONVENTION
    STATUS      current
    DESCRIPTION
        "The TmnxISID specifies a 24 bit (1..16777215) service instance
         identifier for the service. As part of the Shortest Path Bridging
         (SPB) frames, it is used at the destination PE as a demultiplexor
         field."
    SYNTAX      Integer32 (1..16777215)

TmnxSvcEvi                       ::= TEXTUAL-CONVENTION
    STATUS      current
    DESCRIPTION
        "The TmnxSvcEvi specifies an ethernet EVPN identifier value."
    SYNTAX      Integer32 (1..16777215)

TmnxSecRadiusServAlgorithm       ::= TEXTUAL-CONVENTION
    STATUS      current
    DESCRIPTION
        "The TmnxSecRadiusServAlgorithm data type is an enumerated integer that
         indicates the algorithm used to access the list of configured RADIUS
         servers:
         - direct      (1): The first server will be used as primary server for
                            all requests, the second as secondary and so on.
         - round-robin (2): The first server will be used as primary server for
                            the first request, the second server as primary for
                            the second request, and so on. If the router gets
                            to the end of the list, it starts again with the
                            first server."
    SYNTAX      INTEGER {
        direct      (1),
        round-robin (2)
    }

TmnxSvcEviOrZero                 ::= TEXTUAL-CONVENTION
    STATUS      current
    DESCRIPTION
        "The TmnxSvcEviOrZero specifies an ethernet EVPN identifier value. Zero
         indicates no such value specified."
    SYNTAX      Integer32 (0..16777215)

TmnxSubTerminationType           ::= TEXTUAL-CONVENTION
    STATUS      current
    DESCRIPTION
        "The TmnxSubTerminationType indicates how the subscriber host or
         session is terminated."
    SYNTAX      INTEGER {
        local          (1),
        localWholesale (2),
        localRetail    (3)
    }

TmnxSubTerminationTypeOrZero     ::= TEXTUAL-CONVENTION
    STATUS      current
    DESCRIPTION
        "The TmnxSubTerminationType indicates how the subscriber host or
         session is terminated. Zero indicates no subscriber host is
         terminated."
    SYNTAX      INTEGER {
        notApplicable  (0),
        local          (1),
        localWholesale (2),
        localRetail    (3)
    }

TmnxLongDisplayString            ::= TEXTUAL-CONVENTION
    STATUS      current
    DESCRIPTION
        "The TmnxLongDisplayString indicates a long DisplayString."
    SYNTAX      OCTET STRING (SIZE (0..1024))

TmnxLongDisplayStringToBinary    ::= TEXTUAL-CONVENTION
    STATUS      current
    DESCRIPTION
        "The TmnxLongDisplayString indicates a long DisplayString."
    SYNTAX      TmnxLongDisplayString

TmnxLongDisplayStringLegacyBinary ::= TEXTUAL-CONVENTION
    STATUS      current
    DESCRIPTION
        "The TmnxLongDisplayString indicates a long DisplayString."
    SYNTAX      OCTET STRING (SIZE (0..900))

TmnxProxyEntryType               ::= TEXTUAL-CONVENTION
    STATUS      current
    DESCRIPTION
        "The TmnxProxyEntryType indicates type of proxy ARP or ND entry."
    SYNTAX      INTEGER {
        evpn (1),
        stat (2),
        dyn  (3),
        dup  (4)
    }

TmnxCBFClasses                   ::= TEXTUAL-CONVENTION
    STATUS      current
    DESCRIPTION
        "The TmnxCBFClasses indicates a set of forwarding classes."
    SYNTAX      BITS {
        be         (0),
        l2         (1),
        af         (2),
        l1         (3),
        h2         (4),
        ef         (5),
        h1         (6),
        nc         (7),
        defaultLsp (8)
    }

TmnxUrpfCheckMode                ::= TEXTUAL-CONVENTION
    STATUS      current
    DESCRIPTION
        "The TmnxUrpfCheckMode is the mode of operation of Unicast Reverse Path
         Forwarding (uRPF).

         A value of 'strict' means that uRPF checks if the incoming packet has
         a source address that matches a prefix in the routing table, and if
         the interface expects to receive a packet with this source address
         prefix.

         A value of 'loose' means that the uRPF checks if the incoming packet
         has a source address with a corresponding prefix in the routing table,
         but not if the interface expects to receive a packet with a specific
         source address prefix.

         A value of 'strictNoEcmp' means that the uRPF drops a packet with a
         source address that matches an ECMP route and otherwise behaves the
         same as in 'strict' mode."
    SYNTAX      INTEGER {
        strict       (1),
        loose        (2),
        strictNoEcmp (3)
    }

TmnxUserPassword                 ::= TEXTUAL-CONVENTION
    STATUS      current
    DESCRIPTION
        "The value of TmnxUserPassword indicates a password as a plaintext
         string, or as a bcrypt encrypted hash.

         The value of TmnxUserPassword cannot be more than 56 characters if it
         is a plaintext string.

         Any GET request on this type of object returns an empty string."
    SYNTAX      DisplayString (SIZE (0..60))

TmnxUdpPort                      ::= TEXTUAL-CONVENTION
    STATUS      current
    DESCRIPTION
        "The value of TmnxUdpPort is the port used to send messages
         to an event collector target.  514 is the IANA assigned port number
         for syslog.  162 is the IANA assigned port number for SNMP
         notifications."
    SYNTAX      Integer32 (0..65535)

TmnxUuid                         ::= TEXTUAL-CONVENTION
    DISPLAY-HINT "4x-2x-2x-2x-6x"
    STATUS      current
    DESCRIPTION
        "The value of TmnxUuid specifies the Universally Unique Identifier
         (UUID). The UUID consists of 32 hexadecimal digits."
    SYNTAX      OCTET STRING (SIZE (16))

TmnxSyslogFacility               ::= TEXTUAL-CONVENTION
    STATUS      current
    DESCRIPTION
        "The value of TmnxSyslogFacility is an enumerated integer that
         specifies which syslog facility is the intended destination for the
         log event stream."
    REFERENCE
        "The Syslog Protocol (RFC5424): Table 1"
    SYNTAX      INTEGER {
        kernel   (0),
        user     (1),
        mail     (2),
        systemd  (3),
        auth     (4),
        syslogd  (5),
        printer  (6),
        netnews  (7),
        uucp     (8),
        cron     (9),
        authpriv (10),
        ftp      (11),
        ntp      (12),
        logaudit (13),
        logalert (14),
        cron2    (15),
        local0   (16),
        local1   (17),
        local2   (18),
        local3   (19),
        local4   (20),
        local5   (21),
        local6   (22),
        local7   (23)
    }

TmnxSyslogSeverity               ::= TEXTUAL-CONVENTION
    STATUS      current
    DESCRIPTION
        "The value of TmnxSyslogSeverity is an enumerated integer that
         specifies the severity levels of syslog messages."
    REFERENCE
        "The Syslog Protocol (RFC5424): Table 2"
    SYNTAX      INTEGER {
        emergency (0),
        alert     (1),
        critical  (2),
        error     (3),
        warning   (4),
        notice    (5),
        info      (6),
        debug     (7)
    }

TmnxEvpnMultiHomingState         ::= TEXTUAL-CONVENTION
    STATUS      current
    DESCRIPTION
        "The value of TmnxEvpnMultiHomingState indicates multi-homing state of
         the element."
    SYNTAX      INTEGER {
        disabled               (0),
        singleActive           (1),
        singleActiveNoEsiLabel (2),
        allActive              (3),
        allActiveNoEsiLabel    (4)
    }

TmnxBgpEvpnAcEthTag              ::= TEXTUAL-CONVENTION
    STATUS      current
    DESCRIPTION
        "The TmnxBgpEvpnAcEthTag indicates ethernet tag value of the BGP EVPN
         attachment circuit."
    SYNTAX      Integer32 (0..16777215)

TmnxL2tpTunnelGroupName          ::= TEXTUAL-CONVENTION
    STATUS      current
    DESCRIPTION
        "The TmnxL2tpTunnelGroupName data type contains a valid string to
         identify a Layer Two Tunneling Protocol Tunnel Group."
    SYNTAX      DisplayString (SIZE (1..63))

TmnxL2tpTunnelGroupNameOrEmpty   ::= TEXTUAL-CONVENTION
    STATUS      current
    DESCRIPTION
        "The TmnxL2tpTunnelGroupNameOrEmpty data type contains a valid string
         to identify a Layer Two Tunneling Protocol Tunnel Group.

         An empty string indicates that no Tunnel Group is defined."
    SYNTAX      DisplayString (SIZE (0..63))

TmnxLldpManAddressIndex          ::= TEXTUAL-CONVENTION
    STATUS      current
    DESCRIPTION
        "An Index value, used as the index to the table of local port
         management addresses, tmnxLldpConfigManAddrPortsTable. The index
         represents a specific local management address application on the
         system which may, or may not exist."
    SYNTAX      INTEGER {
        oob        (0),
        system     (1),
        systemIpv6 (2),
        oobIpv6    (3)
    }

TFilterID                        ::= TEXTUAL-CONVENTION
    STATUS      current
    DESCRIPTION
        "The identification number of a filter. 0 indicates an invalid
         filter-id."
    SYNTAX      Unsigned32 (0..65535)

TIPFilterID                      ::= TEXTUAL-CONVENTION
    STATUS      current
    DESCRIPTION
        "The identification number of an IP filter."
    SYNTAX      TFilterID

TDHCPFilterID                    ::= TEXTUAL-CONVENTION
    STATUS      current
    DESCRIPTION
        "The identification number of a DHCP filter."
    SYNTAX      TFilterID

TEntryIdOrZero                   ::= TEXTUAL-CONVENTION
    STATUS      current
    DESCRIPTION
        "uniquely identifies an entry in a policy or filter table.
         to facilitate insertion of entries in the tables, we recommend
         assigning entry IDs by 10s:  10, 20, 30, etc.
         The value 0, means that the object does not refer to a filter
         entry at this time."
    SYNTAX      TEntryIndicator (0..65535)

MciBoolean                       ::= TEXTUAL-CONVENTION
    STATUS      current
    DESCRIPTION
        "This provides MCI type to for the objects which do not have well
         defined defaults"
    SYNTAX      INTEGER {
        mciTrue  (1),
        mciFalse (2)
    }

TmnxPppCpState                   ::= TEXTUAL-CONVENTION
    STATUS      current
    DESCRIPTION
        "The TmnxPppCpState data type is an enumerated integer that
         describes the current status of a PPP link.  It can be applied
         to both LCP and NCP links."
    SYNTAX      INTEGER {
        initial     (1),
        starting    (2),
        closed      (3),
        stopped     (4),
        closing     (5),
        stopping    (6),
        requestSent (7),
        ackReceived (8),
        ackSent     (9),
        opened      (10)
    }

TmnxRipNgAuthType                ::= TEXTUAL-CONVENTION
    STATUS      current
    DESCRIPTION
        "The TmnxRipNgAuthType TC defines the authentication method to be
         used for RIP/RIP-NG. Allowed values are :
           noAuthentication(1) - No authentication method
           simplePassword(2)   - Simple password based authentication
              md5(3)              - 16 byte MD5 Authentication
              md20(4)             - 20 byte MD5 Authentication."
    REFERENCE
        "RIP2-MIB.rip2IfConfAuthType"
    SYNTAX      INTEGER {
        noAuthentication (1),
        simplePassword   (2),
        md5              (3),
        md20             (4)
    }

TmnxRipNgAuthKey                 ::= TEXTUAL-CONVENTION
    STATUS      current
    DESCRIPTION
        "The TmnxRipNgAuthKey TC defines the authentication key to be used when
         the authentication type has been configured to either
         simplePassword(2), md5(3) or md20(4) (see TmnxRipNgAuthType)."
    REFERENCE
        "RIP2-MIB.rip2IfConfAuthKey"
    SYNTAX      OCTET STRING (SIZE (0..16))

TmnxAddressAndPrefixType         ::= TEXTUAL-CONVENTION
    STATUS      current
    DESCRIPTION
        ""
    SYNTAX      InetAddressType

TmnxAddressAndPrefixAddress      ::= TEXTUAL-CONVENTION
    STATUS      current
    DESCRIPTION
        ""
    SYNTAX      InetAddress

TmnxAddressAndPrefixPrefix       ::= TEXTUAL-CONVENTION
    STATUS      current
    DESCRIPTION
        ""
    SYNTAX      InetAddressPrefixLength

TmnxIpv6AddressAndPrefixAddress  ::= TEXTUAL-CONVENTION
    STATUS      current
    DESCRIPTION
        ""
    SYNTAX      InetAddressIPv6

TmnxIpv6AddressAndPrefixPrefix   ::= TEXTUAL-CONVENTION
    STATUS      current
    DESCRIPTION
        ""
    SYNTAX      InetAddressPrefixLength

TmnxIpv4AddressAndMaskOrPrefixAddress ::= TEXTUAL-CONVENTION
    STATUS      current
    DESCRIPTION
        ""
    SYNTAX      IpAddress

TmnxIpv4AddressAndMaskOrPrefixMask ::= TEXTUAL-CONVENTION
    STATUS      current
    DESCRIPTION
        ""
    SYNTAX      IpAddress

TmnxIpv4AddressAndMaskOrPrefixPrefix ::= TEXTUAL-CONVENTION
    STATUS      current
    DESCRIPTION
        ""
    SYNTAX      IpAddressPrefixLength

TmnxIpv4AddressAndPrefixAddress  ::= TEXTUAL-CONVENTION
    STATUS      current
    DESCRIPTION
        ""
    SYNTAX      IpAddress

TmnxIpv4AddressAndPrefixPrefix   ::= TEXTUAL-CONVENTION
    STATUS      current
    DESCRIPTION
        ""
    SYNTAX      IpAddressPrefixLength

TmnxIpv6AddressAndMaskOrPrefixAddress ::= TEXTUAL-CONVENTION
    STATUS      current
    DESCRIPTION
        ""
    SYNTAX      InetAddressIPv6

TmnxIpv6AddressAndMaskOrPrefixMask ::= TEXTUAL-CONVENTION
    STATUS      current
    DESCRIPTION
        ""
    SYNTAX      InetAddressIPv6

TmnxIpv6AddressAndMaskOrPrefixPrefix ::= TEXTUAL-CONVENTION
    STATUS      current
    DESCRIPTION
        ""
    SYNTAX      InetAddressPrefixLength

TmnxAddressAndMaskOrPrefixType   ::= TEXTUAL-CONVENTION
    STATUS      current
    DESCRIPTION
        ""
    SYNTAX      InetAddressType

TmnxAddressAndMaskOrPrefixAddress ::= TEXTUAL-CONVENTION
    STATUS      current
    DESCRIPTION
        ""
    SYNTAX      InetAddress

TmnxAddressAndMaskOrPrefixPrefix ::= TEXTUAL-CONVENTION
    STATUS      current
    DESCRIPTION
        ""
    SYNTAX      InetAddressPrefixLength

TmnxAddressAndMaskOrPrefixMask   ::= TEXTUAL-CONVENTION
    STATUS      current
    DESCRIPTION
        ""
    SYNTAX      InetAddress

TmnxAddressWithZoneType          ::= TEXTUAL-CONVENTION
    STATUS      current
    DESCRIPTION
        ""
    SYNTAX      InetAddressType

TmnxAddressWithZoneAddress       ::= TEXTUAL-CONVENTION
    STATUS      current
    DESCRIPTION
        ""
    SYNTAX      InetAddress

THsPirRate                       ::= TEXTUAL-CONVENTION
    STATUS      current
    DESCRIPTION
        "The HS PIR rate to be used in Mbps. The value of
         4294967295(0xFFFFFFFF) means maximum rate."
    SYNTAX      Unsigned32 (1..100000 | 4294967295)

THsPirRateOverride               ::= TEXTUAL-CONVENTION
    STATUS      current
    DESCRIPTION
        "The HS PIR rate to be used in Mbps. The value of
         4294967295(0xFFFFFFFF) means maximum rate. The value of
         4294967294(0xFFFFFFFE) means no override."
    SYNTAX      Unsigned32 (1..100000 | 4294967294 | 4294967295)

THsSchedulerPolicyGroupId        ::= TEXTUAL-CONVENTION
    STATUS      current
    DESCRIPTION
        "The value of THsSchedulerPolicyGroupId specifies the identification
         number of a HS scheduler policy group.  A value of zero (0)
         indicates that no specific group identification has been assigned for
         this object. When an object of type THsSchedulerPolicyGroupId is
         an SNMP table index, an index value of zero (0) is not allowed and a
         noCreation error will be returned."
    SYNTAX      Integer32 (0 | 1)

THsSchedulerPolicyWeight         ::= TEXTUAL-CONVENTION
    STATUS      current
    DESCRIPTION
        "The weight of the specified HS entity while feeding into the parent."
    SYNTAX      Integer32 (1..127)

THsSchedulerPolicyWeightOverride ::= TEXTUAL-CONVENTION
    STATUS      current
    DESCRIPTION
        "The weight of the specified HS entity while feeding into the parent. A
         value of -2 specifies no override."
    SYNTAX      Integer32 (-2 | 1..127)

TmnxWaveKey                      ::= TEXTUAL-CONVENTION
    STATUS      current
    DESCRIPTION
        "The value of TmnxWaveKey specifies the Wavelength to be transmitted on
         the interface's optical signal.

         The following table describes the possible values based on ITU
         channel. Key1 and Key2 must match in modulo 2 with each other.

         Index   ITU          Key 1        Key 2
                channel   First Last      First Last
         -------------------------------------------
            0      61     1548  1548      2032  2032  // 1696 Test Channel

            // Original Tropic Channels (index 1 to 32)
            1      59        1    15       545   559
            2      58       18    32       562   576
            3      57       35    49       579   593
            4      56       52    66       596   610
            5      54       69    83       613   627
            6      53       86   100       630   644
            7      52      103   117       647   661
            8      51      120   134       664   678
            9      49      137   151       681   695
           10      48      154   168       698   712
           11      47      171   185       715   729
           12      46      188   202       732   746
           13      44      205   219       749   763
           14      43      222   236       766   780
           15      42      239   253       783   797
           16      41      256   270       800   814
           17      39      273   287       817   831
           18      38      290   304       834   848
           19      37      307   321       851   865
           20      36      324   338       868   882
           21      34      341   355       885   899
           22      33      358   372       902   916
           23      32      375   389       919   933
           24      31      392   406       936   950
           25      29      409   423       953   967
           26      28      426   440       970   984
           27      27      443   457       987  1001
           28      26      460   474      1004  1018
           29      24      477   491      1021  1035
           30      23      494   508      1038  1052
           31      22      511   525      1055  1069
           32      21      528   542      1072  1086

           // 1696 Extension 42 channels (index 33 to 42)
           33      60     1089  1103      1573  1587
           34      55     1106  1120      1590  1604
           35      50     1123  1137      1607  1621
           36      45     1140  1154      1624  1638
           37      40     1157  1171      1641  1655
           38      35     1174  1188      1658  1672
           39      30     1191  1205      1675  1689
           40      25     1208  1222      1692  1706
           41      20     1225  1239      1709  1723
           42      19     1242  1256      1726  1740

           // 1830 Extension to 44 channels (index 43 and 44)
           43      18     1259  1273      1743  1757
           44      17     1276  1290      1760  1774

           // 1830 Extension to 88 channels (index 45 to 88)
           45     595     1293  1307      1777  1791
           46     585     1310  1324      1794  1808
           47     575     1327  1341      1811  1825
           48     565     1344  1358      1828  1842
           49     545     1361  1375      1845  1859
           50     535     1378  1392      1862  1876
           51     525     1395  1409      1879  1893
           52     515     1412  1426      1896  1910
           53     495     1429  1443      1913  1927
           54     485     1446  1460      1930  1944
           55     475     1463  1477      1947  1961
           56     465     1480  1494      1964  1978
           57     445     1497  1511      1981  1995
           58     435     1514  1528      1998  2012
           59     425     1531  1545      2015  2029
           60     415     1548  1562      2032  2046
           61     395     3585  3599      2049  2063
           62     385     3602  3616      2066  2080
           63     375     3619  3633      2083  2097
           64     365     3636  3650      2100  2114
           65     345     3653  3667      2117  2131
           66     335     3670  3684      2134  2148
           67     325     3687  3701      2151  2165
           68     315     3704  3718      2168  2182
           69     295     3721  3735      2185  2199
           70     285     3738  3752      2202  2216
           71     275     3755  3769      2219  2233
           72     265     3772  3786      2236  2250
           73     245     3789  3803      2253  2267
           74     235     3806  3820      2270  2284
           75     225     3823  3837      2287  2301
           76     215     3840  3854      2304  2318
           77     605     3857  3871      2321  2335
           78     555     3874  3888      2338  2352
           79     505     3891  3905      2355  2369
           80     455     3908  3922      2372  2386
           81     405     3434  3448      3946  3960
           82     355     3451  3465      3963  3977
           83     305     3468  3482      3980  3994
           84     255     3485  3499      3997  4011
           85     205     3502  3516      4014  4028
           86     195     3519  3533      4031  4045
           87     185     3536  3550      4048  4062
           88     175     3553  3567      4065  4079
         -------------------------------------------"
    SYNTAX      Unsigned32 (0..4095)

TmnxSubBondingConnIdOrEmpty      ::= TEXTUAL-CONVENTION
    STATUS      current
    DESCRIPTION
        "The data type TmnxSubBondingConnIdOrEmpty represents the index of the
         bonding connection. The value '0' means that index is not specified."
    SYNTAX      Unsigned32 (0 | 1..2)

TBurstLimitOverride              ::= TEXTUAL-CONVENTION
    STATUS      current
    DESCRIPTION
        "An explicit shaping burst size for a queue. or scheduler or
         aggregate-rate-limit. The value -1 means that the actual value is
         derived from the corresponding buffer policy's default value. A value
         of -2 specifies no override."
    SYNTAX      Integer32 (-2 | -1 | 1..14000000)

TmnxEvpnMHEthSegStatus           ::= TEXTUAL-CONVENTION
    STATUS      current
    DESCRIPTION
        "The TmnxEvpnMHEthSegStatus data type is an enumerated integer that
         describes the status of an ethernet segment associated with the given
         SAP or SDP binding."
    SYNTAX      INTEGER {
        df           (1),
        ndf          (2),
        notesmanaged (3)
    }

TmnxVxlanInstance                ::= TEXTUAL-CONVENTION
    STATUS      current
    DESCRIPTION
        "The TmnxVxlanInstance data type indicates range for the VXLAN
         instance."
    SYNTAX      Unsigned32 (1)

TmnxSvcEvpnMplsTransportType     ::= TEXTUAL-CONVENTION
    STATUS      current
    DESCRIPTION
        "The type of this transport entity."
    SYNTAX      INTEGER {
        invalid       (0),
        local         (1),
        static        (2),
        rsvp          (3),
        ldp           (4),
        ospf          (5),
        isis          (6),
        bgp           (7),
        srTe          (8),
        udp           (9),
        srPolicy      (10),
        mplsFwdPolicy (11),
        ribApi        (12),
        srOspf3       (13)
    }

TmnxMplsLabel                    ::= TEXTUAL-CONVENTION
    STATUS      current
    DESCRIPTION
        "The TmnxMplsLabel data type indicates range for MPLS label."
    SYNTAX      Unsigned32 (32..1048575)

TmnxMplsLabelOrZero              ::= TEXTUAL-CONVENTION
    STATUS      current
    DESCRIPTION
        "The TmnxMplsLabelOrZero data type indicates range for MPLS label. The
         value 0 indicates that no MPLS label is specified."
    SYNTAX      Unsigned32 (0 | 32..1048575)

TmnxMplsLspBandwidth             ::= TEXTUAL-CONVENTION
    STATUS      current
    DESCRIPTION
        "The TmnxMplsLspBandwidth data type indicates maximum bandwidth range."
    SYNTAX      Unsigned32 (0..6400000)

TmnxPrefixSidFullRange           ::= TEXTUAL-CONVENTION
    STATUS      current
    DESCRIPTION
        "The TmnxPrefixSidFullRange data type indicates the full range  of
         possible values for the Prefix SID index or label.

         The available Prefix SID range is restricted by the configured  MPLS
         SR label range."
    SYNTAX      Unsigned32 (0..1048575)

TmnxVni                          ::= TEXTUAL-CONVENTION
    STATUS      current
    DESCRIPTION
        "The TmnxVni data type indicates range for VNI."
    SYNTAX      Unsigned32 (1..16777215)

TmnxVniOrZero                    ::= TEXTUAL-CONVENTION
    STATUS      current
    DESCRIPTION
        "The TmnxVni data type indicates range for VNI."
    SYNTAX      Unsigned32 (0..16777215)

PwPortIdOrZero                   ::= TEXTUAL-CONVENTION
    STATUS      current
    DESCRIPTION
        "PwPortIdOrZero indicates the range for pw port id's with 0 as the
         default value."
    SYNTAX      Unsigned32 (0 | 1..32767)

TmnxCliEngine                    ::= TEXTUAL-CONVENTION
    STATUS      current
    DESCRIPTION
        "The value of TmnxCliEngine specifies the CLI engine type.
         Values:
           classicCli    (1) - Classic CLI engine.
           mdCli         (2) - Model-Driven CLI engine.
           systemDerived (3) - Default value. CLI engine derived from system configuration-mode."
    SYNTAX      INTEGER {
        classicCli    (1),
        mdCli         (2),
        systemDerived (3)
    }

TmnxRsvpSessionNameString        ::= TEXTUAL-CONVENTION
    STATUS      current
    DESCRIPTION
        "The TmnxRsvpSessionNameString type indicates the RSVP session name
         which has extended from 80 to 160 characters."
    SYNTAX      DisplayString (SIZE (0..160))

TmnxQosMdAutoPolicyID            ::= TEXTUAL-CONVENTION
    STATUS      current
    DESCRIPTION
        "The identification number of a policy for Qos objects. This ID must be
         unique within the Qos Domain. The value 0 is used as the null ID."
    SYNTAX      Unsigned32 (0 | 2..65535)

TmnxQosMdAutoIDCount             ::= TEXTUAL-CONVENTION
    STATUS      current
    DESCRIPTION
        "This data type describes the count of policy IDs that has already been
         assigned for Qos objects."
    SYNTAX      Unsigned32 (0..65535)

TmnxNhgDownReason                ::= TEXTUAL-CONVENTION
    STATUS      current
    DESCRIPTION
        "The reason for next-hop group being operationally down."
    SYNTAX      INTEGER {
        notApplicable      (0),
        nextHopNotResolved (1),
        nextHopIsLocal     (3),
        nextHopIsMcast     (4),
        resTypeMismatch    (5)
    }

TmnxQosRateHigh32                ::= TEXTUAL-CONVENTION
    STATUS      current
    DESCRIPTION
        "The upper 32 bits of a 64 bit rate value."
    SYNTAX      TmnxHigh32 (0 | 1 | 4294967295)

TmnxQosRateLow32                 ::= TEXTUAL-CONVENTION
    STATUS      current
    DESCRIPTION
        "The lower 32 bits of a 64 bit rate value."
    SYNTAX      TmnxLow32 (0..4294967295)

AluNgeKeygroupIdOrZero           ::= TEXTUAL-CONVENTION
    STATUS      current
    DESCRIPTION
        "A number used to identify an entry in the aluNgeKeygroupTable or zero."
    SYNTAX      Unsigned32 (0..127)

TmnxEsaNum                       ::= TEXTUAL-CONVENTION
    STATUS      current
    DESCRIPTION
        "The TmnxEsaNum data type contains an identification number for an
         Extended Service Appliance. The value '0' indicates an invalid
         reference."
    SYNTAX      Unsigned32 (0 | 1..16)

TmnxEsaVappNum                   ::= TEXTUAL-CONVENTION
    STATUS      current
    DESCRIPTION
        "The TmnxEsaVappNum type contains an identification number for the
         Virtual Application on an Extended Service Appliance. The value '0'
         indicates an invalid reference."
    SYNTAX      Unsigned32 (0 | 1..4)

TPolRateTypeRefOrLocalLimit      ::= TEXTUAL-CONVENTION
    STATUS      current
    DESCRIPTION
        "The type of the PIR/CIR percent rate. The value 'kbps' means the rate
         is specified in kbps. The value 'percentLocalLimit' means the rate is
         specified in percentage of local limit. The value
         'percentReferPortLimit' means the rate is specified in percentage of
         reference port limit."
    SYNTAX      INTEGER {
        kbps                  (1),
        percentLocalLimit     (2),
        percentReferPortLimit (3)
    }

TPolicerRateTypeWithRefLimit     ::= TEXTUAL-CONVENTION
    STATUS      current
    DESCRIPTION
        "The type of the PIR/CIR percent rate. The value 'kbps' means the rate
         is specified in kbps. The value 'percentPortLimit' means the rate is
         specified in percentage of port limit. The value 'percentLocalLimit'
         means the rate is specified in percentage of local limit. The value
         'percentReferPortLimit' means the rate is specified in percentage of
         reference port limit."
    SYNTAX      INTEGER {
        kbps                  (1),
        percentPortLimit      (2),
        percentLocalLimit     (3),
        percentReferPortLimit (4)
    }

TWredSlopeProfile                ::= TEXTUAL-CONVENTION
    STATUS      current
    DESCRIPTION
        "The profile marking of a packet. Value of 'in' specifies in-profile
         marking. Value of 'out' specifies out-profile marking. Value of 'none'
         specifies the profile marking of the packet will be inherited from the
         existing enqueuing priority derived from earlier matches in the
         classification hierarchy."
    SYNTAX      INTEGER {
        in     (1),
        out    (2),
        exceed (4),
        inplus (5)
    }

TDEWredSlopeProfile              ::= TEXTUAL-CONVENTION
    STATUS      current
    DESCRIPTION
        "This textual convention specifies the profile marking of a packet.

         Value of 'in' specifies the in-profile marking.

         Value of 'out' specifies the out-profile marking.

         Value of 'de' specifies that the profile marking will be based on the DE
         (Drop-Eligible) bit.  DE bit-value of '0' specifies in-profile and DE
         bit value of '1' specifies out-profile marking."
    SYNTAX      INTEGER {
        in     (1),
        out    (2),
        de     (3),
        exceed (4),
        inplus (5)
    }

TmnxFlexAlgoId                   ::= TEXTUAL-CONVENTION
    STATUS      current
    DESCRIPTION
        "TmnxFlexAlgoId identifies a specific Flexible Algorithm in the system."
    SYNTAX      Unsigned32 (128..255)

TmnxFlexAlgoIdOrZero             ::= TEXTUAL-CONVENTION
    STATUS      current
    DESCRIPTION
        "TmnxFlexAlgoId identifies a specific Flexible Algorithm in the system.

         The value '0' indicates that no Flexible Algorithm is specified."
    SYNTAX      Unsigned32 (0 | 128..255)

TmnxAlgorithmId                  ::= TEXTUAL-CONVENTION
    STATUS      current
    DESCRIPTION
        "TmnxAlgorithmId identifies a specific Algorithm in the system.

         The value can identify a defined IGP Algorithm (value 0 is SPF) or a
         Flexible Algorithm (range 128..255)."
    SYNTAX      Unsigned32 (0..255)

TmnxTreeSidOwner                 ::= TEXTUAL-CONVENTION
    STATUS      current
    DESCRIPTION
        "TmnxTreeSidOwner identifies owner information for tree-sid feature."
    SYNTAX      INTEGER {
        none   (0),
        static (1),
        pce    (2),
        srPol  (3)
    }

TmnxTreeSidOrigin                ::= TEXTUAL-CONVENTION
    STATUS      current
    DESCRIPTION
        "TmnxTreeSidOrigin identifies origin information for tree-sid feature."
    SYNTAX      INTEGER {
        pcep          (10),
        bgpSrPolicy   (20),
        configuration (30)
    }

TmnxMacMask                      ::= TEXTUAL-CONVENTION
    STATUS      current
    DESCRIPTION
        "The TmnxMacMask is the 6 byte mask to provide the range of MAC
         addresses."
    SYNTAX      OCTET STRING (SIZE (6))

TmnxVeId                         ::= TEXTUAL-CONVENTION
    STATUS      current
    DESCRIPTION
        "The TmnxVeId is the vpls-edge-range."
    SYNTAX      Integer32 (-1 | 1..65535)

TmnxMcIPsecDomainId              ::= TEXTUAL-CONVENTION
    STATUS      current
    DESCRIPTION
        "TmnxMcIPsecDomainId is an integer identifying a Multi-chassis IPsec
         Domain."
    SYNTAX      Unsigned32 (1..255)

TmnxMcIPsecDomainDesignatedRole  ::= TEXTUAL-CONVENTION
    STATUS      current
    DESCRIPTION
        "TmnxMcIPsecDomainDesignatedRole indicates the designated role of a
         Multi-chassis IPsec Domain."
    SYNTAX      INTEGER {
        standby (1),
        active  (2)
    }

TmnxMcIPsecDomainAdjRmtDesignatedRole ::= TEXTUAL-CONVENTION
    STATUS      current
    DESCRIPTION
        "TmnxMcIPsecDomainAdjRmtDesignatedRole indicated the designated role of
         remote MC IPsec Domain."
    SYNTAX      INTEGER {
        standby (1),
        active  (2),
        unknown (3)
    }

TmnxSubHostSessionLimitOverride  ::= TEXTUAL-CONVENTION
    STATUS      current
    DESCRIPTION
        "The TmnxSubHostSessionLimitOverride data type is an integer that
         indicates the maximum number of hosts using....

         The value -1 indicates that there is no limit

         The value -2 indicates that the AAA server did not specify an
         override."
    SYNTAX      Integer32 (-2..131071)

TPlcyAcctPolicerId               ::= TEXTUAL-CONVENTION
    STATUS      current
    DESCRIPTION
        "The data type describes the router policer accounting template policer
         identifier."
    SYNTAX      Unsigned32 (1..63)

TPktByteOffset                   ::= TEXTUAL-CONVENTION
    STATUS      current
    DESCRIPTION
        "The value, in bytes, of the adjustment to make to the size of each
         packet."
    SYNTAX      Integer32 (-60 | -56 | -52 | -48 | -44 | -40 | -36 | -32 | -28 | -24 | -20 | -16 | -12 | -8 | -4 | 0 | 4 | 8 | 12 | 16 | 20 | 24 | 28 | 32 | 36 | 40 | 44 | 48 | 52 | 56 | 60 | 64)

TmnxAuthAlgorithm                ::= TEXTUAL-CONVENTION
    STATUS      current
    DESCRIPTION
        "TmnxAuthAlgorithm data type is an enumerated integer that describes
         the values used to identify the hashing algorithm.

         Value Descriptions:

         null           - Choosing this value configures the high-speed
                          null algorithm, which does nothing. This is same
                          as not having authentication turned on, same as
                          turning the protocol off.

         md5            - Choosing this value configures the use of
                          hmac-md5 algorithm for authentication.

         sha1           - Choosing this value configures the use of
                          hmac-sha1 algorithm for authentication.

         sha256         - Choosing this value configures the use of
                          hmac-sha256 algorithm for authentication.

         sha384         - Choosing this value configures the use of
                          hmac-sha384 algorithm for authentication.

         sha512         - Choosing this value configures the use of
                           hmac-sha512 algorithm for authentication.

         aesXcbc        - Choosing this value configures the use of
                          aes-xcbc(RFC3566) algorithm for authentication.

         authEncryption - Choosing this value configures the use of
                          Authenticated Encryption (AE) algorithm for
                          authentication."
    SYNTAX      INTEGER {
        null           (1),
        md5            (2),
        sha1           (3),
        sha256         (4),
        sha384         (5),
        sha512         (6),
        aesXcbc        (7),
        authEncryption (8)
    }

TmnxEncrAlgorithm                ::= TEXTUAL-CONVENTION
    STATUS      current
    DESCRIPTION
        "TmnxEncrAlgorithm data type is an enumerated integer that describes
         the values used to identify the encryption algorithm.

         Value Descriptions:

         null          - Choosing this value configures the high-speed
                         null algorithm, which does nothing. This is same
                         as not having encryption turned on.

         des           - Choosing this value configures the 56-bit DES
                         algorithm for encryption. This is an older
                         algorithm with relatively weak security. While
                         better than nothing, it should only be used
                         where a strong algorithm is not available on
                         both ends at an acceptable performance level.

         des3          - Choosing this value configures the 3-DES
                         algorithm for encryption. This is a modified
                         application of the des algorithm which uses
                         multiple des operations to make things more
                         secure.

         aes128        - Choosing this value configures the AES algorithm
                         with a block size of 128 bits. This is a
                         mandatory implementation size for AES. As of
                         today, this is a very strong algorithm choice.

         aes192        - Choosing this value configures the AES algorithm
                         with a block size of 192 bits. This is a
                         stronger version of AES.

         aes256        - Choosing this value configures the AES algorithm
                         with a block size of 256 bits. This is the
                         strongest available version of AES.

         aes128Gcm8     - Choosing this value configures the AES algorithm
                         with a block size of 128 bits in Galois/Counter
                         Mode (GCM) with an 8 octet Integrity Check Value (ICV).

         aes128Gcm12    - Choosing this value configures the AES algorithm
                         with a block size of 128 bits in Galois/Counter
                         Mode (GCM) with an 12 octet ICV.

         aes128Gcm16    - Choosing this value configures the AES algorithm
                         with a block size of 128 bits in Galois/Counter
                         Mode (GCM) with an 16 octet ICV.

         aes192Gcm8     - Choosing this value configures the AES algorithm
                         with a block size of 192 bits in Galois/Counter
                         Mode (GCM) with an 8 octet ICV.

         aes192Gcm12    - Choosing this value configures the AES algorithm
                         with a block size of 192 bits in Galois/Counter
                         Mode (GCM) with an 12 octet ICV.

         aes192Gcm16    - Choosing this value configures the AES algorithm
                         with a block size of 192 bits in Galois/Counter
                         Mode (GCM) with an 16 octet ICV.

         aes256Gcm8     - Choosing this value configures the AES algorithm
                         with a block size of 256 bits in Galois/Counter
                         Mode (GCM) with an 8 octet ICV.

         aes256Gcm12    - Choosing this value configures the AES algorithm
                         with a block size of 256 bits in Galois/Counter
                         Mode (GCM) with an 12 octet ICV.

         aes256Gcm16    - Choosing this value configures the AES algorithm
                         with a block size of 256 bits in Galois/Counter
                         Mode (GCM) with an 16 octet ICV.

         nullAes128Gmac - Choosing this value configures the AES algorithm
                         with a block size of 128 bits in Galois Message
                         Authentication Code (GMAC).

         nullAes192Gmac - Choosing this value configures the AES algorithm
                         with a block size of 192 bits in Galois Message
                         Authentication Code (GMAC).

         nullAes256Gmac - Choosing this value configures the AES algorithm
                         with a block size of 256 bits in Galois Message
                         Authentication Code (GMAC)."
    SYNTAX      INTEGER {
        null           (1),
        des            (2),
        des3           (3),
        aes128         (4),
        aes192         (5),
        aes256         (6),
        aes128Gcm8     (7),
        aes128Gcm12    (8),
        aes128Gcm16    (9),
        aes192Gcm8     (10),
        aes192Gcm12    (11),
        aes192Gcm16    (12),
        aes256Gcm8     (13),
        aes256Gcm12    (14),
        aes256Gcm16    (15),
        nullAes128Gmac (16),
        nullAes192Gmac (17),
        nullAes256Gmac (18)
    }

TmnxIkePolicyDHGroupOrZero       ::= TEXTUAL-CONVENTION
    STATUS      current
    DESCRIPTION
        "TmnxIkePolicyDHGroupOrZero data type is similar to
         TmnxIkePolicyDHGroup but allows the value 'unspecified (0)'."
    SYNTAX      INTEGER {
        unspecified (0),
        group1      (1),
        group2      (2),
        group5      (5),
        group14     (14),
        group15     (15),
        group19     (19),
        group20     (20),
        group21     (21)
    }

TmnxIPsecDirection               ::= TEXTUAL-CONVENTION
    STATUS      current
    DESCRIPTION
        "TmnxIPsecDirection data type is an enumerated integer that describes
         the values used to identify the direction of an IPsec tunnel."
    SYNTAX      INTEGER {
        inbound  (1),
        outbound (2)
    }

TmnxIPsecKeyingType              ::= TEXTUAL-CONVENTION
    STATUS      current
    DESCRIPTION
        "TmnxIPsecKeyingType data type is an enumerated integer that describes
         the values used to identify the IPsec keying type."
    SYNTAX      INTEGER {
        none    (0),
        manual  (1),
        dynamic (2)
    }

TDCpuProtPolicyType              ::= TEXTUAL-CONVENTION
    STATUS      current
    DESCRIPTION
        "TDCpuProtPolicyType data type is an enumerated integer that describes
         the values for distributed CPU protection policy type."
    SYNTAX      INTEGER {
        accessNetwork (1),
        port          (2)
    }

TQosHwAggShaperSchedClass        ::= TEXTUAL-CONVENTION
    STATUS      current
    DESCRIPTION
        "The scheduling class for the specified hardware aggregate shaper
         scheduler entity."
    SYNTAX      Integer32 (1..6)

TSrv6FunctionValue               ::= TEXTUAL-CONVENTION
    STATUS      current
    DESCRIPTION
        "The value to be assigned to all routes for the instance."
    SYNTAX      Unsigned32 (0..1048575)

TSrv6FunctionType                ::= TEXTUAL-CONVENTION
    STATUS      current
    DESCRIPTION
        "The type of function to be assigned to all routes for the instance."
    SYNTAX      INTEGER {
        none    (0),
        dynamic (1),
        static  (2)
    }

TSrv6FunctionErrorCode           ::= TEXTUAL-CONVENTION
    STATUS      current
    DESCRIPTION
        "The error-code for the function."
    SYNTAX      INTEGER {
        noError                (0),
        error                  (1),
        noResource             (2),
        locAdminDown           (3),
        noIntConfig            (4),
        fpeOperDown            (5),
        microSegBlockAdminDown (6)
    }

TSrv6Function                    ::= TEXTUAL-CONVENTION
    STATUS      current
    DESCRIPTION
        "The function for srv6."
    SYNTAX      INTEGER {
        end                         (0),
        end-x                       (1),
        end-dt4                     (2),
        end-dt6                     (3),
        end-dt46                    (4),
        end-dx2                     (5),
        end-dt2u                    (6),
        end-dt2m                    (7),
        un                          (8),
        ua                          (9),
        udt4                        (10),
        udt6                        (11),
        udt46                       (12),
        udx2                        (13),
        udt2u                       (14),
        udt2m                       (15),
        end-b6-encaps-red           (16),
        end-b6-encaps-red-next-csid (17),
        endReplicate                (18)
    }

TSrv6RouteResolution             ::= TEXTUAL-CONVENTION
    STATUS      current
    DESCRIPTION
        "Route resolution options. The options are as follows:

         routeTable: only resolve to an IPv6 route in RTM. If none is found,
         then resolution will fail.

         tunnelTable: only try to resolve the route to a tunnel in TTMv6 i.e.
         the system will try to find an SRv6 policy with a matching color and
         endpoint locator for BGP routes received with an SRv6 TLV and
         therefore containing an SRv6 service SID in TTMv6. If none is found,
         then resolution will fail.

         fallbackTunnelToRouteTable: First try to resolve the route to a tunnel
         in TTMv6. If none is found, then fall back to resolution in RTM. If
         none is still found, then resolution will fail."
    SYNTAX      INTEGER {
        routeTable                 (0),
        tunnelTable                (1),
        fallbackTunnelToRouteTable (2)
    }

TSrv6EndpointBehavior            ::= TEXTUAL-CONVENTION
    STATUS      current
    DESCRIPTION
        "The SRv6 endpoint behaviors."
    SYNTAX      INTEGER {
        none                 (0),
        end                  (1),
        endPsp               (2),
        endUsp               (3),
        endPspUsp            (4),
        endX                 (5),
        endXPsp              (6),
        endXUsp              (7),
        endXPspUsp           (8),
        endT                 (9),
        endTPsp              (10),
        endTUsp              (11),
        endTPspUsp           (12),
        endB6Encaps          (14),
        endBM                (15),
        endDX6               (16),
        endDX4               (17),
        endDT6               (18),
        endDT4               (19),
        endDT46              (20),
        endDX2               (21),
        endDX2V              (22),
        endDT2U              (23),
        endDT2M              (24),
        endB6EncapsRed       (27),
        endUsd               (28),
        endPspUsd            (29),
        endUspUsd            (30),
        endPspUspUsd         (31),
        endXUsd              (32),
        endXPspUsd           (33),
        endXUspUsd           (34),
        endXPspUspUsd        (35),
        endTUsd              (36),
        endTPspUsd           (37),
        endTUspUsd           (38),
        endTPspUspUsd        (39),
        endNxtOnlyCsid       (42),
        endNxtCsid           (43),
        endNxtCsidPsp        (44),
        endNxtCsidUsp        (45),
        endNxtCsidPspUsp     (46),
        endNxtCsidUsd        (47),
        endNxtCsidPspUsd     (48),
        endNxtCsidUspUsd     (49),
        endNxtCsidPspUspUsd  (50),
        endXNxtOnlyCsid      (51),
        endXNxtCsid          (52),
        endXNxtCsidPsp       (53),
        endXNxtCsidUsp       (54),
        endXNxtCsidPspUsp    (55),
        endXNxtCsidUsd       (56),
        endXNxtCsidPspUsd    (57),
        endXNxtCsidUspUsd    (58),
        endXNxtCsidPspUspUsd (59)
    }

TFirBurstLimit                   ::= TEXTUAL-CONVENTION
    STATUS      current
    DESCRIPTION
        "An explicit shaping burst size for a queue. The value of -1 specifies
         system default value."
    SYNTAX      Integer32 (-1 | 1..102400)

TSchedulerMode                   ::= TEXTUAL-CONVENTION
    STATUS      current
    DESCRIPTION
        "The shared queue scheduler mode."
    SYNTAX      INTEGER {
        none    (0),
        vlanQos (1)
    }

TmnxPacketMode                   ::= TEXTUAL-CONVENTION
    STATUS      current
    DESCRIPTION
        "Specifies the packet-mode of an aggregate shaper"
    SYNTAX      INTEGER {
        dataOtwOtw          (0),
        lmotwLmotwOtwAtm    (1),
        lmotwLmotwOtwNonAtm (2),
        otwOtwOtw           (3),
        dataData            (4),
        unknown             (5)
    }

TmnxDPathDomainId                ::= TEXTUAL-CONVENTION
    STATUS      current
    DESCRIPTION
        "The D-Path Domain Id is a 6-octet object. It contains a 4-octet of
         Global Admin Value followed by a 2-octet Local Admin Value."
    SYNTAX      OCTET STRING (SIZE (6))

TmnxTacplusAccessOpType          ::= TEXTUAL-CONVENTION
    STATUS      current
    DESCRIPTION
        "The TmnxTacplusAccessOpType data type is an enumerated integer
         that specifies the access operation for tacplus authorization.
         Values:
           none       (0) - No operation.
           subscriber (1) - Delete operation."
    SYNTAX      INTEGER {
        none   (0),
        delete (1)
    }

TmnxReflectiveQosIndicator       ::= TEXTUAL-CONVENTION
    STATUS      current
    DESCRIPTION
        "The TmnxReflectiveQosIndicator data type specifies the Reflective QoS
         Indicator (RQI) that is inserted along with the QoS Flow Identifier
         (QFI) in the header of data packets of a flow. A value 2 means that no
         RQI is inserted. (See also TmnxQosFlowIdentifier.)"
    SYNTAX      INTEGER {
        false (0),
        true  (1),
        noRQI (2)
    }

TmnxQosFlowIdentifier            ::= TEXTUAL-CONVENTION
    STATUS      current
    DESCRIPTION
        "The TmnxQosFlowIdentifier data type specifies the QoS Flow Identifier
         (QFI) that is inserted along with the Reflective QoS Indicator (RQI)
         in the header of data packets of a flow. A value -1 means that no QFI
         is inserted. (See also TmnxReflectiveQosIndicator.)"
    SYNTAX      Integer32 (-1 | 0..63)

TmnxCamOverloadState             ::= TEXTUAL-CONVENTION
    STATUS      current
    DESCRIPTION
        "The TmnxCamOverloadState data type is an enumerated integer that
         specifies the CAM overload state."
    SYNTAX      INTEGER {
        operational (1),
        nearFull    (2),
        overload    (3)
    }

TmnxCertUpdateStatus             ::= TEXTUAL-CONVENTION
    STATUS      current
    DESCRIPTION
        "The TmnxCertUpdateStatus data type is an enumerated integer that
         specifies the cert update status."
    SYNTAX      INTEGER {
        invalid      (0),
        scheduled    (1),
        inProgress   (2),
        waitForRetry (3)
    }

TmnxDestTEPOperState             ::= TEXTUAL-CONVENTION
    STATUS      current
    DESCRIPTION
        "The TmnxDestTEPOperState data type is an enumerated integer  that
         specifies the operating state of evpn-mpls destination TEP."
    SYNTAX      INTEGER {
        up   (1),
        down (2)
    }

TmnxDestTEPOperFlag              ::= TEXTUAL-CONVENTION
    STATUS      current
    DESCRIPTION
        "The TmnxDestTEPOperFlag data type is an enumerated bit that  specifies
         the conditions affecting the operational status of the  evpn-mpls TEP."
    SYNTAX      BITS {
        serviceMtuMismatch  (0),
        controlWordMismatch (1),
        noL2Comm            (2),
        transportDown       (3),
        serviceDown         (4),
        hashLblMismatch     (5)
    }

TStormCtrlRate                   ::= TEXTUAL-CONVENTION
    STATUS      current
    DESCRIPTION
        "The storm control rate in kbps.

         A value of '-1' means that the storm control burst is set to max."
    SYNTAX      Integer32 (-1 | 22..720000000)

TStormCtrlBurst                  ::= TEXTUAL-CONVENTION
    STATUS      current
    DESCRIPTION
        "The storm control burst in kilobytes.

         A value of '-1' means that the storm control burst is set to max."
    SYNTAX      Integer32 (-1 | 1..4096)

TStormCtrlOprRate                ::= TEXTUAL-CONVENTION
    STATUS      current
    DESCRIPTION
        "The storm control rate in kbps.

         A value of '-1' means that the storm control burst is set to max."
    SYNTAX      Integer32 (-1 | 0 | 22..720000000)

TStormCtrlOprBurst               ::= TEXTUAL-CONVENTION
    STATUS      current
    DESCRIPTION
        "The storm control burst in kilobytes.

         A value of '-1' means that the storm control burst is set to max."
    SYNTAX      Integer32 (-1 | 0 | 1..4161)

TStormCtrlTrafficType            ::= TEXTUAL-CONVENTION
    STATUS      current
    DESCRIPTION
        "The port storm control traffic type."
    SYNTAX      INTEGER {
        broadcast (1),
        multicast (2),
        unicast   (3),
        unknown   (4)
    }

TmnxAttrSetImport                ::= TEXTUAL-CONVENTION
    STATUS      current
    DESCRIPTION
        "The TmnxAttrSetImport data type is an enumerated integer that
         specifies the action taken in attribute-set import:
         -ignore    (1): instructs BGP to ignore ATTR_SET in VPN-IP routes when
                         importing them into this specific VPRN; the ATTR_SET attribute
                         is transmitted unchanged to the CE (default for backwards compatibility).
         -accept    (2): instructs BGP to process ATTR_SET in VPN-IP routes when importing them
                         into this specific VPRN; as part of the normal processing, the ATTR_SET
                         attribute is removed before the route is advertised to CEs.
         -drop      (3): instructs BGP to ignore ATTR_SET in VPN-IP routes when importing them
                         into this specific VPRN; the ATTR_SET attribute is removed before
                         the route is advertised to CEs"
    SYNTAX      INTEGER {
        ignore (1),
        accept (2),
        drop   (3)
    }

TSrv6LocatorType                 ::= TEXTUAL-CONVENTION
    STATUS      current
    DESCRIPTION
        ""
    SYNTAX      INTEGER {
        locator             (0),
        microSegmentLocator (1)
    }

TSrv6ResourceType                ::= TEXTUAL-CONVENTION
    STATUS      current
    DESCRIPTION
        ""
    SYNTAX      INTEGER {
        function (1),
        label    (2),
        lif      (3)
    }

TBgpUntaggedRouteType            ::= TEXTUAL-CONVENTION
    STATUS      current
    DESCRIPTION
        "Type of untagged route type to resolve"
    SYNTAX      INTEGER {
        none           (0),
        untaggedTunnel (1)
    }

TBgpSrv6UpaTriggerNextHop        ::= TEXTUAL-CONVENTION
    STATUS      current
    DESCRIPTION
        " "
    SYNTAX      INTEGER {
        none (0),
        frr  (1)
    }

TEgressQDelayTime                ::= TEXTUAL-CONVENTION
    STATUS      current
    DESCRIPTION
        "Measure delay time"
    SYNTAX      Integer32 (-1 | 0..1000000)

TEgressQDelayPercent             ::= TEXTUAL-CONVENTION
    STATUS      current
    DESCRIPTION
        "Measure delay percent"
    SYNTAX      Integer32 (-1 | 0..10000)

TEgressQBurstLimDelayTime        ::= TEXTUAL-CONVENTION
    STATUS      current
    DESCRIPTION
        "Measure delay time"
    SYNTAX      Unsigned32 (0 | 1..1000000)

TEgressQBurstSizeType            ::= TEXTUAL-CONVENTION
    STATUS      current
    DESCRIPTION
        "Type of delay"
    SYNTAX      INTEGER {
        bytes   (0),
        percent (1),
        time    (2)
    }

TmnxSubAltProfThresholdType      ::= TEXTUAL-CONVENTION
    STATUS      current
    DESCRIPTION
        "The TmnxSubAltProfThresholdType data type is an enumerated integer
         that specifies the threshold type for deciding if the alternate
         sub-profile and/or sla-profile must be used for a subscriber host. See
         tmnxSubAltProfThresholdType."
    SYNTAX      INTEGER {
        none            (0),
        subscriberCount (1)
    }

TmnxPortOptComplianceExtType     ::= TEXTUAL-CONVENTION
    STATUS      current
    DESCRIPTION
        "The TmnxPortOptComplianceExtType is an enumerated integer that extends
         the tmnxPortOpticalCompliance field of of a small form factor (SFF)
         that is inserted into the port"
    REFERENCE
        "SFF Committee document SFF-8024 February 14 2019
         Revision 4.6 Section 4.4."
    SYNTAX      Unsigned32

END
